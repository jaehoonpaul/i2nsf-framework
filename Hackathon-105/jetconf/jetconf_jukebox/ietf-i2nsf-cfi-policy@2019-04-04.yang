module ietf-i2nsf-cfi-policy {
yang-version 1.1;
  namespace
    "urn:ietf:params:xml:ns:yang:ietf-i2nsf-cfi-policy";
  prefix
    cfi-policy;
      
  import ietf-yang-types{
    prefix yang;
    reference
    "Section 3 of RFC 6991";
  }

  import ietf-inet-types{
    prefix inet;
    reference
    "Section 4 of RFC 6991";
  }
      
  organization
    "IETF I2NSF (Interface to Network Security Functions) 
     Working Group";

  contact
    "WG Web: <http://tools.ietf.org/wg/i2nsf>
     WG List: <mailto:i2nsf@ietf.org>

     WG Chair: Adrian Farrel
     <mailto:Adrain@olddog.co.uk>

     WG Chair: Linda Dunbar
     <mailto:Linda.duhbar@huawei.com>

     Editor: Jaehoon Paul Jeong
     <mailto:pauljeong@skku.edu>";
        
  description
   "This module is a YANG module for Consumer-Facing Interface.
   Copyright (c) 2018 IETF Trust and the persons identified as
   authors of the code. All rights reserved.
   Redistribution and use in source and binary forms, with or
   without modification, is permitted pursuant to, and subject
   to the license terms contained in, the Simplified BSD License
   set forth in Section 4.c of the IETF Trust's Legal Provisions
   Relating to IETF Documents
   (http://trustee.ietf.org/license-info).
   This version of this YANG module is part of RFC XXXX; see
   the RFC itself for full legal notices.";


  revision "2019-04-04"{
    description "latest revision";
    reference
      "draft-ietf-consumer-facing-interface-dm-03";
  }

  identity permission-type {
    description 
      "Base identity for the permission types.";
  }

  identity read-only {
    base permission-type;
    description 
      "Identity for read-only permission.";
  }
  identity read-and-write {
    base permission-type;
    description 
      "Identity for read permission.";
  }

  identity scope-type {
    description 
      "Base Identity for scope-type.";
  }
  identity tenant-wide {
    base scope-type;
    description 
      "Base Identity for tenant-wide scope type.";
  }
  identity domain-wide {
    base scope-type;
    description 
      "Base Identity for domain-wide scope type.";
  }

  identity malware-file-type {
    description
      "Base identity for malware file types.";
  }
  identity executable-file {
    base malware-file-type;
    description
      "Identity for executable file types.";
  }
  identity doc-file {
    base malware-file-type;
    description
      "Identity for Microsoft document file types.";
  } 
  identity html-app-file {
    base malware-file-type;
    description
      "Identity for html application file types.";
  }
  identity javascript-file {
    base malware-file-type;
    description
      "Identity for Javascript file types.";
  }
  identity pdf-file {
    base malware-file-type;
    description
      "Identity for pdf file types.";
  }  
  identity dll-file {
    base malware-file-type;
    description
      "Identity for dll file types.";
  }
  identity msi-file {
    base malware-file-type;
    description
      "Identity for Microsoft installer file types.";
  }

  identity security-event-type {
    description
      "Base identity for security event types.";
  }
  identity ddos {
    base malware-file-type;
    description
      "Identity for DDoS event types.";
  }
  identity spyware {
    base malware-file-type;
    description
      "Identity for spyware event types.";
  }
  identity trojan {
    base malware-file-type;
    description
      "Identity for Trojan infection event types.";
  }
  identity ransomeware {
    base malware-file-type;
    description
      "Identity for ransomeware infection event types.";
  }

  identity ipsec-type {
  	description
  	  "Base identity for the IPsec types.";
  }

  identity ike {
  	base ipsec-type;
  	description
  	  "Identity for ipsec-ike";
  }

  identity ikeless {
  	base ipsec-type;
  	description
  	  "Identity for ipsec-ikeless";
  }

  identity continent {
    description
    "Base Identity for continent types.";
  }

  identity africa {
    base continent;
    description
    "Identity for africa.";
  }
  identity asia {
    base continent;
    description
    "Identity for asia.";
  }
  identity europe {
    base continent;
    description
    "Identity for europe.";
  }
  identity north-america {
    base continent;
    description
    "Identity for north-america.";
  }
  identity south-america {
    base continent;
    description
    "Identity for south-america.";
  }
  identity oceania {
    base continent;
    description
    "Identity for Oceania";
  }
  typedef certificate-type {

    type enumeration {
      enum cer {
        description
           "The extension type is '.cer'.";
      }
      enum crt {
        description
           "The extension type is '.crt'.";
      }
      enum key {
        description
           "The extension type is '.key'.";
      }
    }
    description
      "CRT certificate extension, which is used for certificates. 
      The certificates may be encoded as binary DER or as ASCII PEM. 
      The CER and CRT extensions are nearly synonymous.  Most common 
      among *nix systems. CER certificate extension, which is an 
      alternate form of .crt (Microsoft Convention) You can use MS to 
      convert .crt to .cer (.both DER encoded .cer, or base64[PEM] 
      encoded .cer). The KEY extension is used both for public and 
      private PKCS#8 keys. The keys may be encoded as binary DER or 
      as ASCII PEM.";
  }

grouping meta {
  description
    "The purpose of this grouping is to avoid repetition
     of same fields, such as 'name' and 'date'.";
  leaf name {
    type string;
    description "This is the name for an entity.";
  }
  leaf date {
    type yang:date-and-time;
    description "This is the date when the entity is 
    created or modified.";
  }
}

grouping ip-address {
  description
    "There are two types to configure a security policy 
    for IPv4 address, such as exact match and range match.";
    choice match-type {
      description
        "User can choose between 'exact match' and 'range match'.";
      case exact-match {
        leaf-list ip-address {
          type inet:ipv4-address;
          description
          "Exactly matches the IP address specified.";
        }
      }
      case range-match {
        list range-ip-address {
          key "start-ip-address end-ip-address";
          leaf start-ip-address {
            type inet:ipv4-address;
            description
              "Start IP address for a range match.";
          }
          leaf end-ip-address {
            type inet:ip-address;
            description
              "End IP address for a range match.";
          }
          description
            "Range match for an IP-address.";
        }
      }
    }
}

grouping user-group {
  description
    "This grouping is to remove repetition of 
    'name' and 'ip-address' fields.";
  uses meta;
  uses ip-address;
}

grouping device-group {
  description
    "This grouping is to remove repetition of 
    'name', 'ip-address', and 'protocol' fields.";
  uses meta;
  uses ip-address;
  leaf-list protocol {
    type string;
    description
    "This represents the port numbers of devices.";
  }
}

grouping location-group {
  description
    "This grouping is to remove repetition of 
    'name' and 'continent' fields.";
  uses meta;
  leaf continent {
    type identityref {
      base continent;
        }
    description
      "location-group-based on geo-ip of 
      respective continent.";
  }
}

grouping payload-string {
  description
    "This grouping is to remove repetition of 
    'name' and 'content' fields.";
  uses meta;
  leaf-list content {
    type string;
    description
    "This represents the payload string content.";
  }
}

container i2nsf-cfi { 
    description 
    "TBD";
	
  list policy {
    key "policy-name";
    leaf policy-name {
      type string;
      description
        "The name which identifies the policy.";
    }
    description 
    "There can be a multiple number of security rules in
    a policy object. This object is a policy instance to 
    have complete information such as where and when a 
    policy need to be applied.";

    list rule {
      leaf rule-name {
        type string;
        description
        "This represents the name for rules.";
      }
      key "rule-name";
      description
        "There can be a single or multiple number of rules.";

      leaf date {
       type yang:date-and-time;
        description
         "Date this object was created or last 
          modified";
      }
      container event {
        description
         "This represents the event map group name.";
        leaf security-event {
          type identityref {
            base security-event-type;
          }
          description
            "This contains the description of security events.";
        }
        leaf enforce-type {
          type enumeration{
            enum admin-enforced {
              description
                "The enforcement type is admin-enforced.";
            }
            enum time-enforced {
              description
                "The enforcement type is time-enforced.";
            }
            enum event-enforced {
              description
                "The enforcement type is event-enforced.";
            }
          }
          description
            "This field identifies the event of 
            policy enforcement trigger type.";
        }
       container time-information {
        description
          "The container for time-information.";
           leaf begin-time {
             type string;
             description
             "This is start time for time zone";
           }
           leaf end-time {
             type string;
             description
             "This is end time for time zone";
           }
           }
       container recursive {
        description
          "The container to represent the recursiveness
          of the rule.";
         leaf recur {
           type boolean;
           description 
           "recursive enforcement";
         }
         leaf recursive-type{
           type enumeration{
             enum daily {
              description
                "The recursive type is daily.";
             }
             enum weekly {
              description
                "The recursive type is weekly.";
             }
             enum monthly {
              description
                "The recursive type is monthly.";
             }
           }
           description
            "This leaf identifies the recursive type.";
         }
       }
      }
      container condition {
        description
          "The conditions for general security policies.";
            container firewall-condition {
              description
                "The general firewall condition.";
              container source-target {
                description
                  "This represents the source.";
                leaf src-target {
                  type leafref {
                    path "/i2nsf-cfi/policy/endpoint-group/user-group/name";
                  }
                  description 
                  	"This describes the paths to 
                  	the source reference.";  
                }              
              }
              container destination-target {
                description
                  "This represents the destination.";
                  leaf-list dest-target {
                    type leafref {
                      path "/i2nsf-cfi/policy/endpoint-group/user-group/name";
                    }
                    description
                      "This describes the paths to the
                      destination target reference.";
                  }
                }
            }
            container ddos-condition {
              description
                "The condition for DDoS mitigation.";
              container source-target {
                description
                  "This represents the source.";
                leaf-list src-target {
                    type leafref {
                      path "/i2nsf-cfi/policy/endpoint-group/device-group/name";
                    }
                    description
                      "This describes the path to the
                      source target references.";
                }
              }
              container destination-target {
                description
                  "This represents the target.";
                leaf-list dest-target {
                  type leafref {
                    path "/i2nsf-cfi/policy/endpoint-group/device-group/name";
                  }
                  description
                    "This describes the path to the
                    destination target references.";
                }
              }
              container rate-limit {
                description "This describes the rate-limit.";                
                leaf packet-per-second {
                  type uint8;
                  description
                  "The rate-limit limits the amount of incoming packets.";
                }
              }
            }
            container custom-condition {
              description
                "The condition based on packet contents.";
              container source-target {
                description
                  "This represents the source.";
                leaf-list src-target {
                  type leafref {
                    path "/i2nsf-cfi/policy/threat-prevention/payload-content/name";
                  }
                  description 
                  	"Describes the payload string 
                  	content condition source.";
                }                
              }
              container destination-target {
                description
                  "This represents the destination.";
                leaf dest-target {
                  type leafref {
                    path "/i2nsf-cfi/policy/threat-prevention/payload-content/name";
                  }
                  description 
                  	"Describes the payload string 
                  content condition destination.";
                }
              }
            }
            container threat-feed-condition {
              description
                "The condition based on the threat-feed information.";
              container source-target {
                description
                  "This represents the source.";
                leaf-list src-target {
                  type leafref {
                    path "/i2nsf-cfi/policy/threat-prevention/threat-feed-list/name";
                  }
                  description "Describes the threat-feed 
                  condition source.";
                }                
              }
              container destination-target {
                description
                  "This represents the destination.";
                leaf dest-target {
                  type leafref {
                    path "/i2nsf-cfi/policy/threat-prevention/threat-feed-list/name";
                  }
                  description "Describes the threat-feed 
                  condition destination.";
                }
              }
            }
      }
      container action {
        description
          "This is the action container.";
        leaf primary-action {
          type string;
          description
            "This field identifies the action when a rule
            is matched by NSF. The action could be one of
            'PERMIT', 'DENY', 'RATE-LIMIT', 'TRAFFIC-CLASS', 
            'AUTHENTICATE-SESSION', 'IPS, 'APP-FIREWALL', etc.";
        }
        leaf secondary-action {
          type string;
          description
            "This field identifies additional actions if
            a rule is matched. This could be one of 'LOG',
            'SYSLOG', 'SESSION-LOG', etc.";
        }
      }
      container ipsec {
      	description
      	  "This container represents the IPsec-IKE/IKEless cases.";
      	leaf ipsec-method {
      	  type leafref {
      	  	path "/i2nsf-cfi/policy/multi-tenancy/policy-mgnt-auth-method/ipsec/ipsec-method";
      	  }
      	  description
      	  	"This represents the IPsec-method, which
      	  	is defined by policy-mgny-auth-method.";
      	}
      }
      leaf owner {
        type string;
          description
           "This field defines the owner of this 
           policy. Only the owner is authorized to 
           modify the contents of the policy.";
      }
    }

container multi-tenancy {
    description
      "The multi-tenant environment information
       in which the policy is applied. The Rules 
       in the Policy can refer to sub-objects 
       (e.g., domain, tenant, role, and user) of it.";

    list policy-domain {
      uses meta;
      key "name";
      leaf address {
        type string;
        description
          "The address details of the organization 
          or customer.";
      }
      leaf contact {
        type string;
        description
          "contact information of the organization
           or customer.";
      }
      list policy-tenant {
        uses meta;
        key "name";
        description
        "This represents the list of tenants";
        leaf domain {
          type leafref {
            path "/i2nsf-cfi/policy/multi-tenancy/policy-domain/name";
          }
          description
          "This field identifies the domain to which this 
          tenant belongs. This should be reference to a 
          'Policy-Domain??object.";
        }
      }
      leaf authentication-method {
        type leafref {
          path "/i2nsf-cfi/policy/multi-tenancy/policy-mgnt-auth-method/ipsec/ipsec-method";
        }
        description
        "Authentication method to be used for this domain.
        It should be a reference to a 'policy-mgmt-auth-method'
        object.";
      }
      description
        "This represents the list of policy domains.";
    }
    container policy-role {
      uses meta;
      description
      "This represents the list of policy roles.";
      list access-profile {
        uses meta;
        key "name";
        description
          "This field identifies the access profile for the
          role. The profile grants or denies access to policy
          objects.";
        leaf permission-type {
          type identityref {
            base permission-type;
          }
          default read-only;
          description 
            "Permission type for access-profile: read-only 
            or read-and-write.";
        }
      }
    }
    list policy-user {
      uses meta;
      key "name";
      description
      "This represents the policy users.";
      leaf password {
        type string;
        description
          "User password for basic authentication";
      }
      leaf email {
        type string;
        description
          "The email account of a user";
      }
      leaf scope-type {
        type identityref {
          base scope-type;
        }
        default tenant-wide;
        description
          "identifies whether a user has domain-wide
          or tenant-wide privileges";
      }
      leaf role {
        type leafref {
          path "/i2nsf-cfi/policy/multi-tenancy/policy-role/access-profile/name";
        }
        description
          "This represents the reference to the 
          access-profiles.";
      }
    }
    container policy-mgnt-auth-method {
      description
        "This represents the list of authentication methods.";
      leaf auth-method {
        type string;
        description
          "This represents the authentication method name.";
      }
      leaf mutual-authentication {
        type boolean;
          description
          "To identify whether the authentication
          is mutual.";
      }
      list password-based {
      	key "password";
        leaf password {
          type string;
          description
            "This should be defined using the 
            regular expression.";
        }
        description
          "This represents the password-based method.";
      }
      list token-based {
      	key "token";
        leaf token {
          type string;
          description
            "This should be defined according to 
            the token scheme.";
        }
        leaf token-server {
          type inet:ipv4-address;
          description
          	"This represents the token-server 
            information if the authentication method
            is token-based.";
        }
        description
          "This represents the token-based method.";
      }
      list certificate-based {
        key "certificate";
        leaf certificate {
          type certificate-type;
          description
            "This represents the certificate-type.";
        }
        leaf certificate-server {
          type inet:ipv4-address;
            description
              "The certificate-server information if 
               the authentication method is 
               certificate-based";
        }
        description
          "This describes the certificate-based authentication list.";
      }
      list ipsec {
        key "ipsec-method";
        leaf ipsec-method {
          type identityref {
            base ipsec-type;
          }
          description
            "This represents the IPsec-IKE or IPsec-IKEless cases.";
        }
        description
          "This represents the list of IPsec-method.";
      }
      list single-sign-on {
        key "credential";
        leaf credential {
          type certificate-type;
          description
            "This represents the authentication 
            using user credentials.";
        }
        leaf certificate-server {
          type inet:ipv4-address;
            description
              "The certificate-server information if 
              the authentication method is 
              certificate-based";
        }
        description
          "This represents the authentication method 
          for single-sing-on.";
      }
  }
}
container endpoint-group {
        description
          "A logical entity in their business 
          environment, where a security policy 
          is to be applied.";
        list user-group {
          uses user-group;
          key "name";
          description
            "This represents the user group.";
        }
        list device-group {
          uses device-group;
          key "name";
          description
            "This represents the device group.";
        }
        list location-group{
          uses location-group;
          key "name";
          description
            "This represents the location group.";
        }
}
container threat-prevention {
      description
      "this describes the list of threat-prevention.";
      list threat-feed-list {
        uses meta;
        key "name";
          description
          "This represents the threat feed list.";
        container threat-feed-server {
          uses ip-address;
          description
            "This describes the threat-feed server.";
          leaf threat-feed-description {
            type string;
            description 
            "This object containes threat-feed 
            description.";
          }
        }        
        leaf-list threat-file-types {
          type identityref {
            base malware-file-type;
          }
          default executable-file;
          description
            "This contains a list of file types needed to
            be scanned for the virus.";
        }
        leaf-list signatures {
          type string;
          description
            "This contains a list of signatures or hash 
            of the threats.";
        }
      }
      list payload-content {
          uses payload-string;
          key "name";
          description
            "This represents the payload-string group.";
      }
    }
   }
  }
}
