module i2nsf{
  namespace
    "urn:ietf:params:xml:ns:yang:i2nsf";
  prefix
    i2nsf;

  import ietf-inet-types{
    prefix inet;
  }
  import ietf-yang-types{
    prefix yang;
  }

  organization
    "IETF I2NSF (Interface to Network Security Functions)
     Working Group";

  contact
    "WG Web: <http://tools.ietf.org/wg/i2nsf>
     WG List: <mailto:i2nsf@ietf.org>

     WG Chair: Adrian Farrel
     <mailto:Adrain@olddog.co.uk>

     WG Chair: Linda Dunbar
     <mailto:Linda.duhbar@huawei.com>

     Editor: Jaehoon Paul Jeong
     <mailto:pauljeong@skku.edu>";

  description
    "This module defines a YANG data module for consumer-facing
     interface to security controller.";

  revision "2017-10-19"{
    description "Initial revision";
    reference
      "draft-kumar-i2nsf-client-facing-interface-im-02";
  }

  //Groupings
  
  container Policy {
	list rule {
		key rule-name;
		leaf rule-id {
			type string;
		}
		leaf rule-name {
			type string;
		}
		leaf rule-date {
			type yang:date-and-time;
		}
		leaf operation {
			type string;
		}
		list event {
			leaf event-id {
				type string;
			}
			leaf event-name {
				type string;
			}
			leaf event-date {
				type yang:date-and-time;
			}
			leaf event-type{
				type string;
			}
			list time-information {
				leaf start-time {
					type string;
				}
				leaf end-time {
					type string;
				}
			}	
		}
		list condition {
			leaf rule-case {
				type string;
			}
			leaf condition-id {
				type string;
			}
			leaf source {
				type string;
			}
			leaf destination {
				type string;
			}
			leaf match {
				type boolean;
			}
			leaf match-direction {
				type string;
			}
			leaf exception {
				type string;
			}
		}
		list action {
			leaf action-id {
				type string;
			}
			leaf action-name {
				type string;
			}
			leaf action-date {
				type yang:date-and-time;
			}
			leaf primary-action {
				type string;
			}
			leaf secondary-action {
				type string;
			}
		}
		leaf precedence {
			type uint16;
		}
		leaf owner {
			type leafref {
				path "/multi-tenancy/policy-user/policy-user-id";
	    	}
	    }
	}
  }
  container multi-tenancy {
        description
          "The descriptions of multi-tenancy.";

        list policy-domain {
          key "policy-domain-id";
          leaf policy-domain-id {
            type uint16;
            description
              "This represents the list of domains.";
          }
          description
          "this represent the list of policy domains";
          leaf name {
            type string;
            mandatory true;
            description
              "Name of the organization or customer representing 
              this domain.";
          }

          leaf address {
            type string;
            description
              "address of an organization or customer.";
          }

          leaf contact {
            type string;
            mandatory true;
            description
              "contact information of the organization
               or customer.";
          }

          leaf date {
            type yang:date-and-time;
            mandatory true;
            description
              "The date when this account was created 
              or last modified.";
          }

          leaf authentication-method {
            type string;
            mandatory true;
            description
              "The description of authentication method; 
              token-based, password, certificate, 
              single-sign-on";
          }
        }

        list policy-tenant {
          key "policy-tenant-id";
          leaf policy-tenant-id {
            type uint16;
            description
              "The policy tenant id.";
          }
          description
          "This represents the list of tenants";
          leaf name {
            type string;
            mandatory true;
            description
              "Name of the Department or Division within
               an organization.";
          }

          leaf date {
            type yang:date-and-time;
            mandatory true;
            description
              "Date this account was created or last modified.";
          }

          leaf domain {
            type string;
            mandatory true;
            description
            "This field identifies the domain to which this 
            tenant belongs. This should be reference to a 
            ’Policy-Domain’ object.";
          }
        }

        list policy-role {
          key "policy-role-id";
          leaf policy-role-id {
          type uint16;
          mandatory true;
          description
            "This defines a set of permissions assigned 
            to a user in an organization that want to manage 
            its own Security Policies.";
          }
          description
          "This represents the list of policy roles.";
          leaf name {
            type string;
            mandatory true;
            description
              "This field identifies name of the role.";
          }
      
          leaf date {
            type yang:date-and-time;
            mandatory true;
            description
              "Date this role was created or last modified.";
          }

          leaf access-profile {
            type string;
            mandatory true;
            description
              "This field identifies the access profile for the
              role. The profile grants or denies access to policy
              objects.  Multiple access profiles can be 
              concatenated together.";
          }
        }

        list policy-user {
          key "policy-user-id";
          leaf policy-user-id {
          type uint16;
          description
            "This represents the policy-user-id.";
          }
          description
          "This represents the list of policy users.";
          leaf name {
            type string;
            mandatory true;
            description
              "The name of a user.";
          }
      
          leaf date {
            type yang:date-and-time;
            mandatory true;
            description
              "Date this user was created or last modified";
          }

          leaf password {
            type string;
            mandatory true;
            description
              "User password for basic authentication";
          }

          leaf email {
            type string;
            mandatory true;
            description
              "The email account of a user";
          }
          
          leaf scope-type {
            type string;
            description
              "identifies whether a user has domain-wide
              or tenant-wide privileges";
          }

          leaf scope-reference {
            type string;
            description
              "This references policy-domain or policy-tenant 
              to identify the scope.";
          }

          leaf role {
            type string;
            mandatory true;
            description
              "This references policy-role to define specific
              permissions";
          }
        }
  
        list policy-mgmt-auth-method {
          key "policy-mgnt-auth-method-id";
          leaf policy-mgnt-auth-method-id {
          type uint16;
          description
            "This represents the authentication method id.";
          }
          description
          "The descriptions of policy management
            authentication methods.";
          leaf name {
            type string;
            mandatory true;
            description
              "name of the authentication method";
          }

          leaf date {
            type yang:date-and-time;
            mandatory true;
            description
              "date when the authentication method
              was created";
          }

          leaf authentication-method {
            type string;
            mandatory true;
            description
              "The description of authentication method; 
              token-based, password, certificate, 
              single-sign-on";
          }
 
          leaf mutual-authentication {
            type boolean;
            mandatory true;
            description
              "To identify whether the authentication
               is mutual";
          }

          leaf token-server {
            type string;
            mandatory true;
            description
              "The token-server information if the 
              authentication method is token-based";
          }

          leaf certificate-server {
            type string;
            mandatory true;
            description
              "The certificate-server information if 
              the authentication method is certificate-based";
          }

          leaf single-sing-on-server {
            type string;
            mandatory true;
            description
              "The single-sign-on-server information 
              if the authentication method is 
              single-sign-on-based";
          }
        }
      }

    container end-group {
        description
          "A logical entity in their business 
          environment, where a security policy 
          is to be applied.";

        list meta-data-source {
          key "meta-data-source-id";
          leaf meta-data-source-id {
          type uint16;
          mandatory true;
          description
            "This represents the meta-data source id.";
          }
          description
          "This represents the meta-data source.";
          leaf name {
            type string;
            mandatory true;
            description
              "This identifies the name of the 
              meta-datas-ource.";
          }
          leaf date {
            type yang:date-and-time;
            mandatory true;
            description
              "This identifies the date this object was 
              created or last modified.";
          }

          leaf tag-type {
            type boolean;
            description
              "This identifies the group type; user group, 
              app group or device group.";
          }

          leaf tag-server-information {
            type string;
            description
              "The description of suthentication method; 
              token-based, password, certificate, 
              single-sign-on";
          }
          leaf tag-application-protocol {
            type string;
            description
              "This filed identifies the protocol e.g. LDAP, 
              Active Directory, or CMDB";
          }
          leaf tag-server-credential {
            type string;
            description
              "This field identifies the credential 
              information needed to access the tag server";
          }
        }

        list user-group{
          key "user-group-id";
          leaf user-group-id {
          type uint16;
          mandatory true;
          description
            "This represents the the user group id.";
          }
          description
          "This represents the user group.";
          leaf name {
            type string;
            description
              "This field identifies the name of user-group.";
          }

          leaf date {
            type yang:date-and-time;
            description
              "when this user-group was created or last modified.";
          }
          leaf group-type {
            type string;
            description
              "This describes the group type; User-tag, 
              User-name or IP-address.";
          }

          leaf meta-data-server {
            type string;
            description
              "This references metadata source";
          }

          leaf group-member {
            type string;
            description
              "This describes the user-tag information";
          }

          leaf risk-level {
            type uint16;
            description
              "This represents the threat level; valid range
               may be 0 to 9.";
          }
        }

        list device-group{
          key "device-group-id";
          leaf device-group-id {
          type uint16;
           description
            "This represents a device group id.";
          }
          description
            "This represents a device group.";
          leaf name {
            type string;
          description
              "This field identifies the name of 
              a device-group.";
          }
          leaf date {
            type yang:date-and-time;
            description
            "The date when this group was create or 
            last modified.";
          }

          leaf group-type {
            type string;
            description
              "This describes the group type; device-tag, 
              device-name or IP-address.";
          }

          leaf meta-data-server {
            type string;
            description
              "This references meta-data-source 
              object.";
          }

          leaf group-member {
            type string;
            description
              "This describes the device-tag, device-name or 
              IP-address information";
          }

          leaf risk-level {
            type uint16;
            description
              "This represents the threat level; valid range 
              may be 0 to 9.";
          }
       }

       list application-group{
          key "application-group-id";
          leaf application-group-id {
          type uint16;
          description
          "This represents an application group id.";
          }
          description
          "This represents an application group.";
          leaf name {
            type string;
            description
            "This field identifies the name of 
            an application group";
          }

          leaf date {
            type yang:date-and-time;
            description
            "The date when this group was created or 
            last modified.";
          }

          leaf group-type {
            type string;
            description
              "This identifies the group type; 
              application-tag, application-name or
              IP-address.";
          }

          leaf meta-data-server {
            type string;
            description
              "This references meta-data-source 
              object.";
          }

          leaf group-member {
            type string;
            description
              "This describes the application-tag, 
              application-name or IP-address information";
          }

          leaf risk-level {
            type uint16;
            description
              "This represents the threat level; valid range
               may be 0 to 9.";
          }
       }

       list location-group{
          key "location-group-id";
          leaf location-group-id {
          type uint16;
          description
          "This represents a location group id.";
          }
          description
          "This represents a location group.";
          leaf name {
            type string;
            description
            "This field identifies the name of 
            a location group";

          }

          leaf date {
            type yang:date-and-time;
            description
            "The date when this group was created or 
            last modified.";
          }

          leaf group-type {
            type string;
            description
              "This identifies the group type; 
              location-tag, location-name or
              IP-address.";
          }

          leaf meta-data-server {
            type string;
            description
              "This references meta-data-source 
              object.";
          }

          leaf group-member {
            type string;
            description
              "This describes the location-tag, 
              location-name or IP-address information";
          }

          leaf risk-level {
            type uint16;
            description
              "This represents the threat level; valid range
               may be 0 to 9.";
          }
       }
    }

    container threat-feed {
      description
      "this describes the list of threat-feed.";

        list threat-feed {
          key "threat-feed-id";
          leaf threat-feed-id {
          type uint16;
          mandatory true;
          description
            "This represents the threat-feed-id.";
          }
          description
            "This represents the threat feed within the 
            threat-prevention-list.";
          leaf name {
            type string;
            description
              "Name of the theat feed.";
          }

          leaf date {
            type yang:date-and-time;
            description
              "when the threat-feed was created.";
          }

          leaf feed-type {
            type enumeration {
              enum unknown {
                description
                  "feed-type is unknown.";
              }
              enum ip-address {
                description
                  "feed-type is IP address.";
              }
              enum url {
                description
                  "feed-type is URL.";
              }
            }
            mandatory true; 
            description
              "This determined whether the feed-type is IP address 
              based or URL based.";
          }

          leaf feed-server {
            type string;
            description
              "this contains threat feed server information.";
          }

          leaf feed-priority {
            type uint16;
            description
              "this describes the priority of the threat from 
              0 to 5, where 0 means the threat is minimum and
              5 meaning the maximum.";
          }
      }

      list custom-list {
          key "custom-list-id";
          leaf custom-list-id {
          type uint16;
          description
          "this describes the custom-list-id.";
          }
          description
          "this describes the threat-prevention custom list.";
          leaf name {
            type string;
            description
              "Name of the custom-list.";
          }

          leaf date {
            type yang:date-and-time;
            description
              "when the custom list was created.";
          }

          leaf list-type {
            type enumeration {
              enum unknown {
                description
                  "list-type is unknown.";
              }
              enum ip-address {
                description
                  "list-type is IP address.";
              }
              enum mac-address {
                description
                  "list-type is MAC address.";
              }
              enum url {
                description
                  "list-type is URL.";
              }
            }
            mandatory true; 
            description
              "This determined whether the feed-type is IP address 
              based or URL based.";
          }

         leaf list-property {
            type enumeration {
              enum unknown {
                description
                  "list-property is unknown.";
              }
              enum blacklist {
                description
                  "list-property is blacklist.";
              }
              enum whitelist {
                description
                  "list-property is whitelist.";
              }
            }
            mandatory true; 
            description
              "This determined whether the list-type is blacklist 
              or whitelist.";
          }

          leaf list-content {
            type string;
            description
              "This describes the contents of the custom-list.";
          }
      }
      list malware-scan-group {
          key "malware-scan-group-id";
          leaf malware-scan-group-id {
          type uint16;
          mandatory true;
          description
          "This is the malware-scan-group-id.";
          }
          description
          "This represents the malware-scan-group.";
          leaf name {
            type string;
            description
              "Name of the malware-scan-group.";
          }

          leaf date {
            type yang:date-and-time;
            description
              "when the malware-scan-group was created.";
          }

          leaf signature-server {
            type string;
            description
              "This describes the signature server of the 
              malware-scan-group.";
          }
          
          leaf file-types {
            type string;
            description
              "This contains a list of file types needed to
              be scanned for the virus.";
          }

          leaf malware-signatures {
            type string;
            description
              "This contains a list of malware signatures or hash.";
          }
      }

      list event-map-group {
          key "event-map-group-id";
          leaf event-map-group-id {
          type uint16;
          mandatory true;
          description
          "This is the event-map-group-id.";
          }
          description
          "This represents the event map group.";
      
          leaf name {
            type string;
            description
              "Name of the event-map.";
          }

          leaf date {
            type yang:date-and-time;
            description
              "when the event-map was created.";
          }

          leaf security-events {
            type string;
            description
              "This contains a list of security events.";
          }

          leaf threat-map {
            type string;
            description
              "This contains a list of threat levels.";
          }
        }
      }
  }
