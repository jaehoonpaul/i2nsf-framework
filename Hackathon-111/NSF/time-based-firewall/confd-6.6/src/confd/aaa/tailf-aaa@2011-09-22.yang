module tailf-aaa {
  namespace "http://tail-f.com/ns/aaa/1.1";
  prefix aaa;
  tailf:id "http://tail-f.com/ns/aaa";

  import tailf-common {
    prefix tailf;
  }

  organization "Tail-f Systems";

  description
    "This module defines the Tail-f AAA data model.";

  revision 2011-09-22 {
    description
      "Released as part of ConfD-3.7.";
  }

  revision 2010-06-17 {
    description
      "Released as part of ConfD-3.3.";
  }

  revision 2010-04-22 {
    description
      "Released as part of ConfD-3.2.1.";
  }

  revision 2010-03-18 {
    description
      "Released as part of ConfD-3.2.";
  }

  typedef history {
    type uint64 {
      range "0 .. 8192";
    }
  }
  typedef idle-timeout {
    type uint64 {
      range "0 .. 8192";
    }
  }
  typedef display-level {
    type uint64 {
      range "1 .. 64";
    }
  }
  typedef dataOperationType {
    type enumeration {
      enum r;
      enum rx;
      enum x;
      enum rw;
      enum rwx;
      enum wx;
      enum w;
      enum c;
      enum cr;
      enum cu;
      enum cd;
      enum cx;
      enum cru;
      enum crd;
      enum crx;
      enum cud;
      enum cux;
      enum cdx;
      enum crud;
      enum crux;
      enum crdx;
      enum cudx;
      enum crudx;
      enum ru;
      enum rd;
      enum rud;
      enum rux;
      enum rdx;
      enum u;
      enum ud;
      enum ux;
      enum d;
      enum dx;
    }
  }
  typedef cmdOperationType {
    type enumeration {
      enum r;
      enum rx;
      enum x;
    }
  }
  typedef Action {
    type enumeration {
      enum accept;
      enum reject;
      enum accept_log;
    }
  }
  typedef passwdStr {
    type tailf:md5-digest-string {
    }
  }
  typedef levelInt {
    type int32 {
      range "0 .. 15";
    }
  }
  typedef modeStr {
    type union {
      type string;
      type builtinModes;
    }
  }
  typedef builtinModes {
    type enumeration {
      enum exec;
      enum configure;
    }
  }

  grouping session-params {
    leaf complete-on-space {
      type boolean;
      tailf:info "Enable/disable completion on space";
    }
    leaf ignore-leading-space {
      type boolean;
      tailf:info "Ignore leading whitespace";
    }
    leaf idle-timeout {
      type idle-timeout;
      tailf:info "CLI idle-timeout in seconds";
    }
    leaf paginate {
      type boolean;
      tailf:info "Paginate output from CLI commands";
    }
    leaf history {
      type history;
      tailf:info "History size";
    }
    leaf autowizard {
      type boolean;
      tailf:info "Automatically query user for mandatory elems";
    }
    leaf show-defaults {
      type boolean;
      tailf:info "Show default values when showing the configuration";
    }
    leaf display-level {
      type display-level;
      tailf:info "Max depth to show when displaying configuration";
    }
    leaf prompt1 {
      type string;
      tailf:info "Prompt for operational mode";
    }
    leaf prompt2 {
      type string;
      tailf:info "Prompt for configure mode";
    }
  }

  container aaa {
    tailf:info "AAA management";
    container authentication {
      tailf:info "User management";
      container users {
        tailf:info "List of local users";
        list user {
          key name;
          max-elements 1024;
          leaf name {
            type string;
            tailf:info "Login name of the user";
          }
          leaf uid {
            type int32;
            mandatory true;
            tailf:info "User Identifier";
          }
          leaf gid {
            type int32;
            mandatory true;
            tailf:info "Group Identifier";
          }
          leaf password {
            type passwdStr;
            mandatory true;
          }
          leaf ssh_keydir {
            type string;
            mandatory true;
            tailf:info "Absolute path to directory where user's ssh keys
                        may be found";
          }
          leaf homedir {
            type string;
            mandatory true;
            tailf:info "Absolute path to user's home directory";
          }
        }
      }
      container groups {
        list group {
          key name;
          max-elements 32;
          leaf name {
            type string;
            tailf:info "Name of group";
          }
          leaf gid {
            type int32;
            tailf:info "Optional Group Identifier";
          }
          leaf users {
            type string;
            mandatory true;
            tailf:info "Space separated string of users that are members
                        of the group";
          }
        }
      }
    }
    container authorization {
      tailf:info "Authorization management";
      container cmdrules {
        tailf:info "List of command rules";
        list cmdrule {
          key index;
          tailf:indexed-view;

          leaf index {
            type uint32;
          }
          leaf context {
            type string;
            mandatory true;
            tailf:info "The 'context' to match, '*' | cli | netconf | webui
                       | snmp | an arbitrary string from maapi calls";
          }
          leaf command {
            type string;
            mandatory true;
            tailf:info "The command to match";
          }
          leaf group {
            type string;
            mandatory true;
            tailf:info "The group of the user";
          }
          leaf ops {
            type cmdOperationType;
            mandatory true;
            tailf:info "Type of command";
          }
          leaf action {
            type Action;
            mandatory true;
            tailf:info "Action for this rule";
          }
        }
      }
      container datarules {
        list datarule {
          key index;
          tailf:indexed-view;

          leaf index {
            type uint32;
          }
          leaf namespace {
            type string;
            mandatory true;
            tailf:info "XML namespace to match or '*'";
          }
          leaf context {
            type string;
            default *;
            tailf:info "The 'context' to match, '*' | cli | netconf | webui
                       | snmp | an arbitrary string from maapi calls";
          }
          leaf keypath {
            type string;
            mandatory true;
            tailf:info "The path in the data tree to match, e.g /aaa";
          }
          leaf group {
            type string;
            mandatory true;
            tailf:info "The group of the user";
          }
          leaf ops {
            type dataOperationType;
            mandatory true;
            tailf:info "Operation type";
          }
          leaf action {
            type Action;
            mandatory true;
            tailf:info "Action for this rule";
          }
        }
      }
    }
    container ios {
      tailf:info "Specific IOS settings";
      presence "";

      list level {
        key nr;
        min-elements 2;
        leaf nr {
          type levelInt;
        }
        leaf secret {
          type passwdStr;
        }
        leaf password {
          type passwdStr;
        }
        leaf prompt {
          type string;
          default '\h# ';
        }
      }

      list privilege {
        key mode;
        leaf mode {
          type modeStr;
        }
        list level {
          key nr;
          min-elements 1;
          max-elements 15;
          leaf nr {
            type levelInt;
          }
          list command {
            key name;
            leaf name {
              type string;
            }
          }
        }
      }
    }
  }
  list alias {
    key name;
    tailf:info "Create command alias.";
    leaf name {
      type string;
      tailf:info "Name of the command alias. An alias name can be a single
                  word or multiple words joined by a dash (-).";
    }
    leaf expansion {
      type string;
      mandatory true;
      tailf:info "Original command syntax. Valid abbreviations of the original
                  command syntax can be entered for the command-syntax
                  argument.";
    }
  }
  container session {
    uses session-params;
    presence "";
    tailf:info "Global default CLI session parameters";
  }
  list user {
    tailf:info "User specific command aliases and default CLI session
                parameters";
    key name;
    leaf name {
      type string;
    }
    leaf description {
      type string;
      tailf:info "User description";
    }
    list alias {
      key name;
      tailf:info "Create command alias.";
      leaf name {
        type string;
        tailf:info "Name of the command alias. An alias name can be a single
                    word or multiple words joined by a dash (-).";
      }
      leaf expansion {
        type string;
        mandatory true;
        tailf:info "Original command syntax. Valid abbreviations of the original
                    command syntax can be entered for the command-syntax
                    argument.";
      }
    }
    container session {
      uses session-params;
      tailf:info "User specific default CLI session parameters";
    }
  }

}
