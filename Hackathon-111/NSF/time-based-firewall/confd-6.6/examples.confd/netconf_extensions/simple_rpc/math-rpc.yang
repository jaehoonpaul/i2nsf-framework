module math-rpc {
  namespace "http://example.com/math";
  prefix math;

  import tailf-common {
    prefix tailf;
  }

  grouping math-input {
    choice op {
      container add {
        leaf-list operand {
          type int32;
          min-elements 2;
          max-elements 2;
        }
      }
      container sub {
        leaf-list operand {
          type int32;
          min-elements 2;
          max-elements 2;
        }
      }
    }
  }

  grouping math-output {
    leaf result {
      type int32;
    }
  }

  rpc math {
    tailf:exec "./math" {
      tailf:wd ".";
      tailf:raw-xml;
    }
    input {
      uses math-input;
    }
    output {
      uses math-output;
    }
  }

  rpc math2 {
    tailf:exec "./math2" {
      tailf:wd ".";
    }
    input {
      uses math-input;
    }
    output {
      uses math-output;
    }
  }

  rpc math3 {
    tailf:actionpoint math3;
    input {
      uses math-input;
    }
    output {
      uses math-output;
    }
  }

  tailf:error-info {
    uses math-input;
  }
}
