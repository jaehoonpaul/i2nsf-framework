module tailf-confd-monitoring-ann {
  namespace "urn:dummy";
  prefix dummy;

  import tailf-common {
    prefix tailf;
  }
  import tailf-confd-monitoring {
    prefix tfcm;
  }


  tailf:annotate "/tfcm:confd-state" {
    tailf:callpoint "confd" {
      tailf:internal;
    }

    tailf:info "Display ConfD status information";
  }
}
