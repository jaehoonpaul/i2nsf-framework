module ietf-ipv6-unicast-routing-ann {
    namespace "urn:dummy";
    prefix "dummy";

    import tailf-common {
        prefix tailf;
    }

    import ietf-routing {
        prefix rt;
    }

    import ietf-ipv6-unicast-routing {
        prefix v6ur;
    }

    // default Linux limitation - only one "protocol instance" running;
    // might by different in case of some VRF / networking namespace
    // functionality support
    tailf:annotate "/rt:routing/rt:control-plane-protocols"
        + "/rt:control-plane-protocol/rt:static-routes"
        + "/v6ur:ipv6/v6ur:route" {
        must "count(/rt:routing/rt:control-plane-protocols"
           + "/rt:control-plane-protocol/rt:static-routes"
           + "/v6ur:ipv6/v6ur:route[v6ur:destination-prefix=current()"
           + "/v6ur:destination-prefix]) = 1" {
             error-message "Cannot configure same destination-prefix of route"
                         + " on two different control-plane-protocols!";
        }
    }
}
