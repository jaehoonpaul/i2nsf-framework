module ietf-i2nsf-policy-rule-for-nsf {
  yang-version 1.1;
  namespace 
    "urn:ietf:params:xml:ns:yang:ietf-i2nsf-policy-rule-for-nsf";
  prefix
    nsfintf;

  import ietf-inet-types{
    prefix inet;
    reference "RFC 6991";
  }
  import ietf-yang-types{
    prefix yang;
    reference "RFC 6991";
  }
  
  organization
    "IETF I2NSF (Interface to Network Security Functions) 
     Working Group";

  contact
    "WG Web: <http://tools.ietf.org/wg/i2nsf>
     WG List: <mailto:i2nsf@ietf.org>

	 Editor: Jinyong Tim Kim 
     <mailto:timkim@skku.edu>
    
     Editor: Jaehoon Paul Jeong
     <mailto:pauljeong@skku.edu>";

  description
    "This module is a YANG module for Network Security Functions
     (NSF)-Facing Interface.
	 
     Copyright (c) 2021 IETF Trust and the persons identified as
     authors of the code. All rights reserved.
	 
     Redistribution and use in source and binary forms, with or
     without modification, is permitted pursuant to, and subject to
     the license terms contained in, the Simplified BSD License set
     forth in Section 4.c of the IETF Trust's Legal Provisions
     Relating to IETF Documents
     (https://trustee.ietf.org/license-info).
	 
     This version of this YANG module is part of RFC XXXX
     (https://www.rfc-editor.org/info/rfcXXXX); see the RFC itself
     for full legal notices.";
  
  revision "2021-04-06"{
    description "The latest revision.";
    reference
      "RFC XXXX: I2NSF Network Security Function-Facing Interface 
       YANG Data Model";
  } 
  
  /*
   * Identities
   */
   
  identity priority-usage-type {
    description 
      "Base identity for priority usage type.";
  }
  
  identity priority-by-order {
    base priority-usage-type;
    description 
      "Identity for priority by order";
  }
  
  identity priority-by-number {
    base priority-usage-type;
    description 
      "Identity for priority by number";
  }
  
  identity event {
    description
      "Base identity for policy events";
    reference
      "draft-ietf-i2nsf-nsf-monitoring-data-model-04: I2NSF NSF
       Monitoring YANG Data Model - Event";
  }
  
  identity system-event {
    base event;
    description 
      "Identity for system events";
    reference
      "draft-ietf-i2nsf-nsf-monitoring-data-model-04: I2NSF NSF
       Monitoring YANG Data Model - System event";	   
  }
  
  identity system-alarm {
    base event;
    description 
      "Identity for system alarms";
    reference
      "draft-ietf-i2nsf-nsf-monitoring-data-model-04: I2NSF NSF
       Monitoring YANG Data Model - System alarm";	
  }
  
  identity access-violation {
    base system-event;
    description
      "Identity for access violation
      system events";
    reference
      "draft-ietf-i2nsf-nsf-monitoring-data-model-04: I2NSF NSF
       Monitoring YANG Data Model - System event for access
       violation";
  }
  
  identity configuration-change {
    base system-event;
    description 
      "Identity for configuration change
      system events";
    reference
      "draft-ietf-i2nsf-nsf-monitoring-data-model-04: I2NSF NSF
       Monitoring YANG Data Model - System event for configuration
       change";	   
  }
  
  identity memory-alarm {
    base system-alarm;
    description
      "Identity for memory alarm 
      system alarms";
    reference
      "draft-ietf-i2nsf-nsf-monitoring-data-model-04: I2NSF NSF
       Monitoring YANG Data Model - System alarm for memory";	   
  }
  
  identity cpu-alarm {
    base system-alarm;
    description
      "Identity for CPU alarm 
      system alarms";
    reference
      "draft-ietf-i2nsf-nsf-monitoring-data-model-04: I2NSF NSF
       Monitoring YANG Data Model - System alarm for CPU";	   
  }

  identity disk-alarm {
    base system-alarm;
    description 
      "Identity for disk alarm 
      system alarms";
    reference
      "draft-ietf-i2nsf-nsf-monitoring-data-model-04: I2NSF NSF
       Monitoring YANG Data Model - System alarm for disk";	   
  }

  identity hardware-alarm {
    base system-alarm;
    description 
      "Identity for hardware alarm 
      system alarms";
    reference
      "draft-ietf-i2nsf-nsf-monitoring-data-model-04: I2NSF NSF
       Monitoring YANG Data Model - System alarm for hardware";	   
  }

  identity interface-alarm {
    base system-alarm;
    description 
      "Identity for interface alarm 
      system alarms";
    reference
      "draft-ietf-i2nsf-nsf-monitoring-data-model-04: I2NSF NSF
       Monitoring YANG Data Model - System alarm for interface";	   
  }  
  
  identity fragmentation-flags-type {
    description 
      "Base identity for fragmentation flags type";
    reference
      "RFC 791: Internet Protocol - Fragmentation Flags";
  }

  identity fragment {
    base fragmentation-flags-type;
    description 
      "Identity for 'More fragment' flag";
    reference
      "RFC 791: Internet Protocol - Fragmentation Flags";
  }
  
  identity no-fragment {
    base fragmentation-flags-type;
    description 
      "Identity for 'Do not fragment' flag";
    reference
      "RFC 791: Internet Protocol - Fragmentation Flags";
  }
  
  identity reserved {
    base fragmentation-flags-type;
    description 
      "Identity for reserved flags";
    reference
      "RFC 791: Internet Protocol - Fragmentation Flags";
  }
  
  identity protocol {
    description 
      "Base identity for protocol of IPv4";
    reference
      "IANA: Assigned Internet Protocol Numbers
      RFC 791: Internet Protocol - Protocol";
  }

  identity next-header {
    description
      "Base identity for IPv6 next header";
    reference
      "RFC 8200: Internet Protocol, Version 6 (IPv6) 
      Specification - Next Header";  
  }
  
  identity icmp {
    base protocol;
    base next-header;
    description 
      "Identity for ICMP IPv4 protocol and 
      IPv6 next header";
    reference
      "IANA: Assigned Internet Protocol Numbers   
       RFC  791: Internet Protocol - Protocol
       RFC 8200: Internet Protocol, Version 6 (IPv6) 
       Specification - Next Header";
  }
  
  identity igmp {
    base protocol;
    base next-header;
    description 
      "Identity for IGMP IPv4 protocol and 
      IPv6 next header";
    reference
      "IANA: Assigned Internet Protocol Numbers 
       RFC  791: Internet Protocol - Protocol
       RFC 8200: Internet Protocol, Version 6 (IPv6) 
       Specification - Next Header";
  }
  
  identity tcp {
    base protocol;
    base next-header;
    description 
      "Identity for TCP protocol";
    reference
      "IANA: Assigned Internet Protocol Numbers 
       RFC  791: Internet Protocol - Protocol
       RFC 8200: Internet Protocol, Version 6 (IPv6) 
       Specification - Next Header";
  }
  
  identity igrp {
    base protocol;
    base next-header;
    description 
      "Identity for IGRP IPv4 protocol 
      and IPv6 next header";
    reference
      "IANA: Assigned Internet Protocol Numbers   
       RFC  791: Internet Protocol - Protocol
       RFC 8200: Internet Protocol, Version 6 (IPv6) 
       Specification - Next Header";
  }
  
  identity udp {
    base protocol;
    base next-header;
    description 
      "Identity for UDP IPv4 protocol 
      and IPv6 next header";
    reference
      "IANA: Assigned Internet Protocol Numbers  
       RFC  791: Internet Protocol - Protocol
       RFC 8200: Internet Protocol, Version 6 (IPv6) 
       Specification - Next Header";
  }
  
  identity gre {
    base protocol;
    base next-header;
    description 
      "Identity for GRE IPv4 protocol
      and IPv6 next header";
    reference
      "IANA: Assigned Internet Protocol Numbers 
       RFC  791: Internet Protocol - Protocol
       RFC 8200: Internet Protocol, Version 6 (IPv6) 
       Specification - Next Header";
  }
  
  identity esp {
    base protocol;
    base next-header;
    description 
      "Identity for ESP IPv4 protocol 
      and IPv6 next header";
    reference
      "IANA: Assigned Internet Protocol Numbers	   
       RFC  791: Internet Protocol - Protocol
       RFC 8200: Internet Protocol, Version 6 (IPv6) 
       Specification - Next Header";
  }
  
  identity ah {
    base protocol;
    base next-header;
    description 
      "Identity for AH IPv4 protocol 
      and IPv6 next header";
    reference
      "IANA: Assigned Internet Protocol Numbers
       RFC  791: Internet Protocol - Protocol
       RFC 8200: Internet Protocol, Version 6 (IPv6) 
       Specification - Next Header";
  }
  
  identity mobile {
    base protocol;
    base next-header;
    description 
      "Identity for mobile IPv4 protocol 
      and IPv6 next header";
    reference
      "IANA: Assigned Internet Protocol Numbers   
       RFC  791: Internet Protocol - Protocol
       RFC 8200: Internet Protocol, Version 6 (IPv6) 
       Specification - Next Header";
  }
  
  identity tlsp {
    base protocol;
    base next-header;
    description 
      "Identity for TLSP IPv4 protocol 
      and IPv6 next header";
    reference
      "IANA: Assigned Internet Protocol Numbers   
       RFC  791: Internet Protocol - Protocol
       RFC 8200: Internet Protocol, Version 6 (IPv6) 
       Specification - Next Header";
  }
  
  identity skip {
    base protocol;
    base next-header;
    description 
      "Identity for skip IPv4 protocol 
      and IPv6 next header";
    reference
      "IANA: Assigned Internet Protocol Numbers   
       RFC  791: Internet Protocol - Protocol
       RFC 8200: Internet Protocol, Version 6 (IPv6) 
       Specification - Next Header";
  }
  
  identity ipv6-icmp {
    base protocol;
    base next-header;
    description 
      "Identity for IPv6 ICMP next header";
    reference
      "IANA: Assigned Internet Protocol Numbers
       RFC 4443: Internet Control Message Protocol (ICMPv6)
       for the Internet Protocol Version 6 (IPv6) Specification
	   RFC 8200: Internet Protocol, Version 6 (IPv6) 
       Specification - Next Header";
  }  
  
  identity eigrp {
    base protocol;
    base next-header;
    description 
      "Identity for EIGRP IPv4 protocol 
      and IPv6 next header";
    reference
      "IANA: Assigned Internet Protocol Numbers 
       RFC  791: Internet Protocol - Protocol
       RFC 8200: Internet Protocol, Version 6 (IPv6) 
       Specification - Next Header";
  }
  
  identity ospf {
    base protocol;
    base next-header;
    description 
      "Identity for OSPF IPv4 protocol 
      and IPv6 next header";
    reference
      "IANA: Assigned Internet Protocol Numbers
       RFC  791: Internet Protocol - Protocol
       RFC 8200: Internet Protocol, Version 6 (IPv6) 
       Specification - Next Header";
  }
  
  identity l2tp {
    base protocol;
    base next-header;
    description 
      "Identity for L2TP IPv4 protocol 
      and IPv6 next header";
    reference
      "IANA: Assigned Internet Protocol Numbers
       RFC  791: Internet Protocol - Protocol
       RFC 8200: Internet Protocol, Version 6 (IPv6) 
       Specification - Next Header";
  }

  identity ipopts {
    description
      "Base identity for IP options";
    reference
      "RFC 791: Internet Protocol - Options";
  }
  
  identity rr {
    base ipopts;
    description
      "Identity for 'Record Route' IP Option";
    reference
      "RFC 791: Internet Protocol - Options";
  }
  
  identity eol {
    base ipopts;
    description
      "Identity for 'End of List' IP Option";
    reference
      "RFC 791: Internet Protocol - Options";
  }
  
  identity nop {
    base ipopts;
    description
      "Identity for 'No Operation' IP Option";
    reference
      "RFC 791: Internet Protocol - Options";
  }
  
  identity ts {
    base ipopts;
    description
      "Identity for 'Timestamp' IP Option";
    reference
      "RFC 791: Internet Protocol - Options";
  }
  
  identity sec {
    base ipopts;
    description
      "Identity for 'IP security' IP Option";
    reference
      "RFC 791: Internet Protocol - Options"; 
  }
  
  identity esec {
    base ipopts;
    description
      "Identity for 'IP extended security' IP Option";
    reference
      "RFC 791: Internet Protocol - Options";
  }
  
  identity lsrr {
    base ipopts;
    description
      "Identity for 'Loose Source Routing' IP Option";
    reference
      "RFC 791: Internet Protocol - Options";
  }
  
  identity ssrr {
    base ipopts;
    description
      "Identity for 'Strict Source Routing' IP Option";
    reference
      "RFC 791: Internet Protocol - Options";
  }
  
  identity satid {
    base ipopts;
    description
      "Identity for 'Stream Identifier' IP Option";
    reference
      "RFC 791: Internet Protocol - Options";
  }
  
  identity any {
    base ipopts;
    description
      "Identity for 'any IP options 
      included in IPv4 packet";
    reference
      "RFC 791: Internet Protocol - Options";
  }
  
  identity tcp-flags {
    description
      "Base identity for TCP flags";
    reference
      "RFC 793: Transmission Control Protocol - Flags";
  }
  
  identity cwr {
    base tcp-flags;
    description
      "Identity for 'Congestion Window Reduced' TCP flag";
    reference
      "RFC 793: Transmission Control Protocol - Flags";
  }
  
  identity ecn {
    base tcp-flags;
    description
      "Identity for 'Explicit Congestion Notification' 
      TCP flag";
    reference
      "RFC 793: Transmission Control Protocol - Flags";
  }
  
  identity urg {
    base tcp-flags;
    description
      "Identity for 'Urgent' TCP flag";
    reference
      "RFC 793: Transmission Control Protocol - Flags";
  }

  identity ack {
    base tcp-flags;
    description
      "Identity for 'acknowledgement' TCP flag";
    reference
      "RFC 793: Transmission Control Protocol - Flags";
  }
  
  identity psh {
    base tcp-flags;
    description
      "Identity for 'Push' TCP flag";
    reference
      "RFC 793: Transmission Control Protocol - Flags"; 
  }
  
  identity rst {
    base tcp-flags;
    description
      "Identity for 'Reset' TCP flag";
    reference
      "RFC 793: Transmission Control Protocol - Flags";
  }
  
  identity syn {
    base tcp-flags;
    description
      "Identity for 'Synchronize' TCP flag";
    reference
      "RFC 793: Transmission Control Protocol - Flags";
  }
  
  identity fin {
    base tcp-flags;
    description
      "Identity for 'Finish' TCP flag";
    reference
      "RFC 793: Transmission Control Protocol - Flags";
  }
  
  identity icmp-type {
    description
      "Base identity for ICMP Message types";
    reference
      "RFC 792: Internet Control Message Protocol";
  }
  
  identity echo-reply {
    base icmp-type;
    description
      "Identity for 'Echo Reply' ICMP message type";
    reference
      "RFC 792: Internet Control Message Protocol";
  }
  
  identity destination-unreachable {
    base icmp-type;
    description
      "Identity for 'Destination Unreachable'
      ICMP message type";
    reference
      "RFC 792: Internet Control Message Protocol";
  }
  
  
  identity redirect {
    base icmp-type;
    description
      "Identity for 'Redirect' ICMP message type";
    reference
      "RFC 792: Internet Control Message Protocol";
  }
  
  identity echo {
    base icmp-type;
    description
      "Identity for 'Echo' ICMP message type";
    reference
      "RFC 792: Internet Control Message Protocol";
  }
  
  identity router-advertisement {
    base icmp-type;
    description
      "Identity for 'Router Advertisement' 
      ICMP message type";
    reference
      "RFC 792: Internet Control Message Protocol";
  }
  
  identity router-solicitation {
    base icmp-type;
    description
      "Identity for 'Router Solicitation' 
      ICMP message type";
    reference
      "RFC 792: Internet Control Message Protocol";
  }
  
  identity time-exceeded {
    base icmp-type;
    description
      "Identity for 'Time exceeded' ICMP message type";
    reference
      "RFC 792: Internet Control Message Protocol";
  }
  
  identity parameter-problem {
    base icmp-type;
    description
      "Identity for 'Parameter Problem'
      ICMP message type";
    reference
      "RFC 792: Internet Control Message Protocol";
  }
  
  identity timestamp {
    base icmp-type;
    description
      "Identity for 'Timestamp' ICMP message type";
    reference
      "RFC 792: Internet Control Message Protocol";
  }
  
  identity timestamp-reply {
    base icmp-type;
    description
      "Identity for 'Timestamp Reply'
      ICMP message type";
    reference
      "RFC 792: Internet Control Message Protocol";
  }
  
  identity datagram-conversion-error {
    base icmp-type;
    description
      "Identity for 'Datagram Conversion Error'
      ICMP message type";
    reference
      "RFC 792: Internet Control Message Protocol";
  }
  
  identity experimental-mobility-protocols {
    base icmp-type;
    description
      "Identity for 'Experimental Mobility Protocols'
      ICMP message type";
    reference
      "RFC 792: Internet Control Message Protocol";
  }
  
  identity extended-echo-request {
    base icmp-type;
    description
      "Identity for 'Extended Echo Request'
      ICMP message type";
    reference
      "RFC  792: Internet Control Message Protocol
       RFC 8335: PROBE: A Utility for Probing Interfaces";
  }
  
  identity extended-echo-reply {
    base icmp-type;
    description
      "Identity for 'Extended Echo Reply'
      ICMP message type";
    reference
      "RFC  792: Internet Control Message Protocol
       RFC 8335: PROBE: A Utility for Probing Interfaces";
  }
  
  identity net-unreachable {
    base icmp-type;
    description
      "Identity for net unreachable
      in destination unreachable types";
    reference
      "RFC 792: Internet Control Message Protocol";
  }
  
  identity host-unreachable {
    base icmp-type;
    description
      "Identity for host unreachable
      in destination unreachable types";
    reference
      "RFC 792: Internet Control Message Protocol";
  }
  
  identity protocol-unreachable {
    base icmp-type;
    description
      "Identity for protocol unreachable
      in destination unreachable types";
    reference
      "RFC 792: Internet Control Message Protocol";
  }
  
  identity port-unreachable {
    base icmp-type;
    description
      "Identity for port unreachable
      in destination unreachable types";
    reference
      "RFC 792: Internet Control Message Protocol";
  }
  
  identity fragment-set {
    base icmp-type;
    description
      "Identity for fragmentation set
      in destination unreachable types";
    reference
      "RFC 792: Internet Control Message Protocol";
  }
  
  identity source-route-failed {
    base icmp-type;
    description
      "Identity for source route failed
      in destination unreachable types";
    reference
      "RFC 792: Internet Control Message Protocol";
  }
  
  identity destination-network-unknown {
    base icmp-type;
    description
      "Identity for destination network unknown
      in destination unreachable types";
    reference
      "RFC 792: Internet Control Message Protocol";
  }
  
  identity destination-host-unknown {
    base icmp-type;
    description
      "Identity for destination host unknown
      in destination unreachable types";
    reference
      "RFC 792: Internet Control Message Protocol";
  }
  
  identity source-host-isolated {
    base icmp-type;
    description
      "Identity for source host isolated
      in destination unreachable types";
    reference
      "RFC 792: Internet Control Message Protocol";
  }
  
  identity communication-prohibited-with-destination-network {
    base icmp-type;
    description
      "Identity for which communication with destination network 
      is administratively prohibited in destination unreachable 
      types";
    reference
      "RFC 792: Internet Control Message Protocol";
  }
  
  identity communication-prohibited-with-destination-host {
    base icmp-type;
    description
      "Identity for which communication with destination host
      is administratively prohibited in destination unreachable 
      types";
    reference
      "RFC 792: Internet Control Message Protocol";
  }
  
  identity destination-network-unreachable-for-tos {
    base icmp-type;
    description
      "Identity for destination network unreachable 
      for type of service in destination unreachable types";
    reference
      "RFC 792: Internet Control Message Protocol";
  }
  
  identity destination-host-unreachable-for-tos {
    base icmp-type;
    description
      "Identity for destination host unreachable 
      for type of service in destination unreachable types";
    reference
      "RFC 792: Internet Control Message Protocol";
  }
  
  identity communication-prohibited {
    base icmp-type;
    description
      "Identity for communication administratively prohibited 
      in destination unreachable types";
    reference
      "RFC 792: Internet Control Message Protocol";
  }

  identity host-precedence-violation {
    base icmp-type;
    description
      "Identity for host precedence violation 
      in destination unreachable types";
    reference
      "RFC 792: Internet Control Message Protocol";
  }
  
  identity precedence-cutoff-in-effect {
    base icmp-type;
    description
      "Identity for precedence cutoff in effect
      in destination unreachable types";
    reference
      "RFC 792: Internet Control Message Protocol";
  }
  
  identity redirect-datagram-for-the-network {
    base icmp-type;
    description
      "Identity for redirect datagram for the network 
      (or subnet) in redirect types";
    reference
      "RFC 792: Internet Control Message Protocol";
  }
  
  identity redirect-datagram-for-the-host {
    base icmp-type;
    description
      "Identity for redirect datagram for the host
      in redirect types";
    reference
      "RFC 792: Internet Control Message Protocol";
  }
  
  identity redirect-datagram-for-the-tos-and-network {
    base icmp-type;
    description
      "Identity for redirect datagram for the type of 
      service and network in redirect types";
    reference
      "RFC 792: Internet Control Message Protocol";
  }
  
  identity redirect-datagram-for-the-tos-and-host {
    base icmp-type;
    description
      "Identity for redirect datagram for the type of 
      service and host in redirect types";
    reference
      "RFC 792: Internet Control Message Protocol";
  }
  
  identity normal-router-advertisement {
    base icmp-type;
    description
      "Identity for normal router advertisement
      in router advertisement types";
    reference
      "RFC 792: Internet Control Message Protocol";
  }
  
  identity does-not-route-common-traffic {
    base icmp-type;
    description
      "Identity for does not route common traffic
      in router advertisement types";
    reference
      "RFC 792: Internet Control Message Protocol";
  }
  
  identity time-to-live-exceeded-in-transit {
    base icmp-type;
    description
      "Identity for time to live exceeded in transit
      in time exceeded types";
    reference
      "RFC 792: Internet Control Message Protocol";
  }
  
  identity fragment-reassembly-time-exceeded {
    base icmp-type;
    description
      "Identity for fragment reassembly time exceeded
      in time exceeded types";
    reference
      "RFC 792: Internet Control Message Protocol";
  }
  
  identity pointer-indicates-the-error {
    base icmp-type;
    description
      "Identity for pointer indicates the error
      in parameter problem types";
    reference
      "RFC 792: Internet Control Message Protocol";
  }
  
  identity missing-a-required-option {
    base icmp-type;
    description
      "Identity for missing a required option
      in parameter problem types";
    reference
      "RFC 792: Internet Control Message Protocol";
  }
  
  identity bad-length {
    base icmp-type;
    description
      "Identity for bad length
      in parameter problem types";
    reference
      "RFC 792: Internet Control Message Protocol";
  }
  
  identity bad-spi {
    base icmp-type;
    description
      "Identity for bad spi";
    reference
      "RFC 792: Internet Control Message Protocol";
  }
  
  identity authentication-failed {
    base icmp-type;
    description
      "Identity for authentication failed";
    reference
      "RFC 792: Internet Control Message Protocol";
  }
  
  identity decompression-failed {
    base icmp-type;
    description
      "Identity for decompression failed";
    reference
      "RFC 792: Internet Control Message Protocol";
  }
  
  identity decryption-failed {
    base icmp-type;
    description
      "Identity for decryption failed";
    reference
      "RFC 792: Internet Control Message Protocol";
  }
  
  identity need-authentication {
    base icmp-type;
    description
      "Identity for need authentication";
    reference
      "RFC 792: Internet Control Message Protocol";
  }
  
  identity need-authorization {
    base icmp-type;
    description
      "Identity for need authorization";
    reference
      "RFC 792: Internet Control Message Protocol";
  }
  
  identity req-no-error {
    base icmp-type;
    description
      "Identity for request with no error
      in extended echo request types";
    reference
      "RFC  792: Internet Control Message Protocol
       RFC 8335: PROBE: A Utility for Probing Interfaces";
  }

  identity rep-no-error {
    base icmp-type;
    description
      "Identity for reply with no error
      in extended echo reply types";
    reference
      "RFC  792: Internet Control Message Protocol
       RFC 8335: PROBE: A Utility for Probing Interfaces";
  }
  
  identity malformed-query {
    base icmp-type;
    description
      "Identity for malformed query
      in extended echo reply types";
    reference
      "RFC  792: Internet Control Message Protocol
       RFC 8335: PROBE: A Utility for Probing Interfaces";
  }
  
  identity no-such-interface {
    base icmp-type;
    description
      "Identity for no such interface
      in extended echo reply types";
    reference
      "RFC  792: Internet Control Message Protocol
       RFC 8335: PROBE: A Utility for Probing Interfaces";
  }
  
  identity no-such-table-entry {
    base icmp-type;
    description
      "Identity for no such table entry
      in extended echo reply types";
    reference
      "RFC  792: Internet Control Message Protocol
       RFC 8335: PROBE: A Utility for Probing Interfaces";
  }
  
  identity multiple-interfaces-satisfy-query {
    base icmp-type;
    description
      "Identity for multiple interfaces satisfy query
      in extended echo reply types";
    reference
      "RFC  792: Internet Control Message Protocol
       RFC 8335: PROBE: A Utility for Probing Interfaces";
  }
 
  identity target-device {
    description
      "Base identity for target devices";
    reference
      "draft-ietf-i2nsf-capability-data-model-15: 
       I2NSF Capability YANG Data Model";
  }

  identity computer {
    base target-device;
    description 
      "Identity for computer such as personal computer (PC)
       and server";
  }
 
  identity mobile-phone {
    base target-device;
    description 
      "Identity for mobile-phone such as smartphone and
       cellphone";
  }
  
  identity voip-volte-phone {
    base target-device;
    description 
      "Identity for voip-volte-phone";
  }
  
  identity tablet {
    base target-device;
    description 
      "Identity for tablet";
  }
  
  identity network-infrastructure-device {
    base target-device;
    description 
      "Identity for network infrastructure devices
       such as switch, router, and access point";
  }
  
  identity iot {
    base target-device;
    description 
      "Identity for IoT (Internet of Things)";
  }
  
  identity vehicle {
    base target-device;
    description 
      "Identity for vehicle that connects to and shares
       data through the Internet";
  }
  
  identity content-security-control {
    description
      "Base identity for content security control";
    reference
      "RFC 8329: Framework for Interface to 
       Network Security Functions - Flow-Based 
       NSF Capability Characterization
       draft-ietf-i2nsf-capability-data-model-15:
       I2NSF Capability YANG Data Model";
  }
  
  identity firewall {
    base content-security-control;
    description 
      "Identity for firewall that monitors 
       incoming and outgoing network traffic 
       and permits or blocks data packets based 
       on a set of security rules.";
  }
  
  identity antivirus {
    base content-security-control;
    description 
      "Identity for antivirus that prevents, 
       scans, detects and deletes viruses 
       from a computer";
  }
  
  identity ips {
    base content-security-control;
    description
      "Identity for IPS (Intrusion Prevention System) 
       that prevents malicious activity within a network";
  }
  
  identity ids {
    base content-security-control;
    description
      "Identity for IDS (Intrusion Detection System) 
       that detects malicious activity within a network";
  }
  
  identity url-filtering {
    base content-security-control;
    description
      "Identity for url filtering that 
       limits access by comparing the web traffic's URL 
       with the URLs for web filtering in a database";
  }
  
  identity mail-filtering {
    base content-security-control;
    description
      "Identity for mail filtering that 
       filters out a malicious email message by 
       comparing its sender email address with the email
       addresses of malicious users in a database";
  }
  
  identity file-blocking {
    base content-security-control;
    description
      "Identity for file blocking that blocks the
       download or upload of malicious files with the
       information of suspicious files in a database";
  }
  
  identity pkt-capture {
    base content-security-control;
    description
      "Identity for packet capture that 
       intercepts a packet that is crossing or moving
       over a specific network.";
  }
  
  identity application-control {
    base content-security-control;
    description
      "Identity for application control that 
       filters out the packets of malicious applications
       with the information of those applications in a
       database";
  }
  
  identity voip-volte {
    base content-security-control;
    description
      "Identity for VoIP/VoLTE security service that 
       filters out the packets of malicious users 
       with a blacklist of malicious users in a database";
  }
  
  identity attack-mitigation-control {
    description
      "Base identity for attack mitigation control";
    reference
      "RFC 8329: Framework for Interface to 
       Network Security Functions - Flow-Based 
       NSF Capability Characterization
       draft-ietf-i2nsf-capability-data-model-15:
       I2NSF Capability YANG Data Model";
  }

  identity syn-flood {
    base attack-mitigation-control;
    description
      "Identity for syn flood
       that weakens the SYN flood attack";
  }

  identity udp-flood {
    base attack-mitigation-control;
    description
      "Identity for udp flood
       that weakens the UDP flood attack";
  }

  identity icmp-flood {
    base attack-mitigation-control;
    description
      "Identity for icmp flood
       that weakens the ICMP flood attack";
  }

  identity ip-frag-flood {
    base attack-mitigation-control;
    description
      "Identity for ip frag flood
       that weakens the IP fragmentation flood attack";
  }

  identity http-and-https-flood {
    base attack-mitigation-control;
    description
      "Identity for http and https flood
       that weakens the HTTP and HTTPS flood attack";
  }

  identity dns-flood {
    base attack-mitigation-control;
    description
      "Identity for dns flood
       that weakens the DNS flood attack";
  }

  identity dns-amp-flood {
    base attack-mitigation-control;
    description
      "Identity for dns amp flood
       that weakens the DNS amplification flood attack";
  }

  identity ntp-amp-flood {
    base attack-mitigation-control;
    description
      "Identity for ntp amp flood
       that weakens the NTP amplification flood attack";
  }

  identity ssl-ddos {
    base attack-mitigation-control;
    description
      "Identity for ssl ddos
       that weakens the SSL DDoS attack";
  }

  identity ip-sweep {
    base attack-mitigation-control;
    description
      "Identity for ip sweep
       that weakens the IP sweep attack";
  }

  identity port-scanning {
    base attack-mitigation-control;
    description
      "Identity for port scanning
       that weakens the port scanning attack";
  }

  identity ping-of-death {
    base attack-mitigation-control;
    description
      "Identity for ping-of-death
       that weakens the ping-of-death attack";
  }  
  
  identity teardrop {
    base attack-mitigation-control;
    description
      "Identity for teardrop
       that weakens the teardrop attack";
  }  

  identity oversized-icmp {
    base attack-mitigation-control;
    description
      "Identity for oversized icmp
       that weakens the oversized icmp attack";
  }  

  identity tracert {
    base attack-mitigation-control;
    description
      "Identity for tracert
       that weakens the tracert attack";
  }    
  
  identity ingress-action {
    description
      "Base identity for action";
    reference
      "draft-ietf-i2nsf-capability-data-model-15:
       I2NSF Capability YANG Data Model - Ingress Action";
  }    
  
  identity egress-action {
    description
      "Base identity for egress action";
    reference
      "draft-ietf-i2nsf-capability-data-model-15:
       I2NSF Capability YANG Data Model - Egress Action";
  }    
  
  identity default-action {
    description
      "Base identity for default action";
    reference
      "draft-ietf-i2nsf-capability-data-model-15:
       I2NSF Capability YANG Data Model - Default Action";
  }    
  
  identity pass {
    base ingress-action;
    base egress-action;
    base default-action;
    description
      "Identity for pass";
    reference
      "draft-ietf-i2nsf-capability-data-model-15:
       I2NSF Capability YANG Data Model - Actions and
       Default Action";
  }
  
  identity drop {
    base ingress-action;
    base egress-action;
    base default-action;
    description
      "Identity for drop";
    reference
      "draft-ietf-i2nsf-capability-data-model-15:
       I2NSF Capability YANG Data Model - Actions and
       Default Action";
  }
  
  identity rate-limit {
    base ingress-action;
    base egress-action;
    base default-action;
    description
      "Identity for rate limiting action";
    reference
      "draft-ietf-i2nsf-capability-data-model-15:
       I2NSF Capability YANG Data Model - Actions and
       Default Action";
  }

  identity mirror {
    base ingress-action;
    base egress-action;
    base default-action;
    description
      "Identity for mirror";
    reference
      "draft-ietf-i2nsf-capability-data-model-15:
       I2NSF Capability YANG Data Model - Actions and
       Default Action";
  }
  
  identity log-action {
    description
      "Base identity for log action";
  }    
  
  identity rule-log {
    base log-action;
    description
      "Identity for rule log";
  }
  
  identity session-log {
    base log-action;
    description
      "Identity for session log";
  }
  
  identity invoke-signaling {
    base egress-action;
    description
      "Identity for invoke signaling";
  }
 
  identity tunnel-encapsulation {
    base egress-action;
    description
      "Identity for tunnel encapsulation";
  }
  
  identity forwarding {
    base egress-action;
    description
      "Identity for forwarding";
  }
  
  identity redirection {
    base egress-action;
    description
      "Identity for redirection";

  }
  
  identity resolution-strategy {
    description 
      "Base identity for resolution strategy";
    reference
      "draft-ietf-i2nsf-capability-data-model-15:
       I2NSF Capability YANG Data Model - Resolution Strategy";
  }    
  
  identity fmr {
    base resolution-strategy;
    description 
      "Identity for First Matching Rule (FMR)";
    reference
      "draft-ietf-i2nsf-capability-data-model-15:
       I2NSF Capability YANG Data Model - Resolution Strategy";
  }

  identity lmr {
    base resolution-strategy;
    description 
      "Identity for Last Matching Rule (LMR)";
    reference
      "draft-ietf-i2nsf-capability-data-model-15:
       I2NSF Capability YANG Data Model - Resolution Strategy";
  }
  
  identity pmr {
    base resolution-strategy;
    description 
      "Identity for Prioritized Matching Rule (PMR)";
    reference
      "draft-ietf-i2nsf-capability-data-model-15:
       I2NSF Capability YANG Data Model - Resolution Strategy";
  }
  
  identity pmre {
    base resolution-strategy;
    description 
      "Identity for Prioritized Matching Rule
      with Errors (PMRE)";
    reference
      "draft-ietf-i2nsf-capability-data-model-15:
       I2NSF Capability YANG Data Model - Resolution Strategy";
  }
  
  identity pmrn {
    base resolution-strategy;
    description 
      "Identity for Prioritized Matching Rule 
      with No Errors (PMRN)";
    reference
      "draft-ietf-i2nsf-capability-data-model-15:
       I2NSF Capability YANG Data Model - Resolution Strategy";
  }
  
  identity day {
    description
      "This represents the base for days.";
  }
  
  identity monday {
    base day;
    description
      "This represents Monday.";
  }
  
  identity tuesday {
    base day;
    description
      "This represents Tuesday.";
  }
  
  identity wednesday {
    base day;
    description
      "This represents Wednesday.";
  }
  
  identity thursday {
    base day;
    description
      "This represents Thursday.";
  }
  
  identity friday {
    base day;
    description
      "This represents Friday.";
  }
  
  identity saturday {
    base day;
    description
      "This represents Saturday.";
  }
  
  identity sunday {
    base day;
    description
      "This represents Sunday.";
  }
  
  
  /*
   * Groupings
   */ 
  
  grouping ipv4 {
    list ipv4-address {
      key "ipv4";
      description
        "The list of IPv4 addresses.";
    
      leaf ipv4 {
        type inet:ipv4-address;
        description
          "The value of IPv4 address.";
      }
      choice subnet {
        description
          "The subnet can be specified as a prefix length or
          netmask.";
        leaf prefix-length {
          type uint8 {
            range "0..32";
          }
          description
            "The length of the subnet prefix.";
        }
        leaf netmask {
          type yang:dotted-quad;
          description
            "The subnet specified as a netmask.";
        }
      }
    }
    description
      "Grouping for an IPv4 address";

    reference
      "RFC  791: Internet Protocol - IPv4 address
       RFC 8344: A YANG Data Model for IP Management";
  }
        
  grouping ipv6 {
    list ipv6-address {
      key "ipv6";
      description
        "The list of IPv6 addresses.";
    
      leaf ipv6 {
        type inet:ipv6-address;
        description
          "The value of IPv6 address.";
      }
      
      leaf prefix-length {
        type uint8 {
          range "0..128";
        }
        description
          "The length of the subnet prefix.";
      }
    }
    description
      "Grouping for an IPv6 address";
      
    reference
      "RFC 8200: Internet Protocol, Version 6 (IPv6) 
       Specification - IPv6 address
       RFC 8344: A YANG Data Model for IP Management";
  }
  
  grouping pkt-sec-ipv4 {
    list range-ipv4-address {
      key "start-ipv4-address end-ipv4-address";
      leaf start-ipv4-address {
        type inet:ipv4-address;
        description
          "Starting IPv4 address for a range match.";
      }
          
      leaf end-ipv4-address {
        type inet:ipv4-address;
        description
          "Ending IPv4 address for a range match.";
      }
      description
        "Range match for an IPv4 address.";
    }
    description
      "Grouping for the IPv4 addresses.";
      
    reference
      "RFC 791: Internet Protocol - IPv4 address";
  }
  
  grouping pkt-sec-ipv6 {
    list range-ipv6-address {
      key "start-ipv6-address end-ipv6-address";
      leaf start-ipv6-address {
        type inet:ipv6-address;
        description
          "Starting IPv6 address for a range match.";
      }
          
      leaf end-ipv6-address {
        type inet:ipv6-address;
        description
          "Ending IPv6 address for a range match.";
      }
      description
        "Range match for an IPv6 address.";
    }
    description
      "Grouping for IPv6 address.";
      
    reference
      "RFC 8200: Internet Protocol, Version 6 (IPv6) 
       Specification - IPv6 address";
  }
  
  grouping pkt-sec-port-number {
    list range-port-num {
      key "start-port-num end-port-num";
      leaf start-port-num {
        type inet:port-number;
        description
          "Starting port number for a range match.";
      }
      leaf end-port-num {
        type inet:port-number;
        description
          "Ending port number for a range match.";
      }
      description
        "Range match for a port number.";
    }
    description
      "Grouping for port number.";
      
    reference
      "RFC 793: Transmission Control Protocol - Port number
       RFC 768: User Datagram Protocol - Port Number";
  }
  
  /*
   * Data nodes
   */
  
  list i2nsf-security-policy {
    description
      "Container for security policy
       including a set of security rules according to certain logic, 
       i.e., their similarity or mutual relations, etc. The network
       security policy can be applied to both the unidirectional
       and bidirectional traffic across the NSF.
       The I2NSF security policies use the Event-Condition-Action 
       (ECA) policy model ";
       
    reference
      "RFC 8329: Framework for Interface to Network Security 
       Functions - I2NSF Flow Security Policy Structure
       draft-ietf-i2nsf-capability-data-model-15:
       I2NSF Capability YANG Data Model - Design Principles and
       ECA Policy Model Overview";

    key "system-policy-name";           
    leaf system-policy-name {
      type string;
      description
        "The name of the policy. 
         This must be unique.";
    }  
   
    leaf priority-usage {
      type identityref {
        base priority-usage-type;
      }
      default priority-by-order;
      description
        "Priority usage type for security policy rule: 
         priority by order and priority by number";
    }
    
    leaf resolution-strategy {
      type identityref {
        base resolution-strategy;
      }
      default fmr;
      description 
        "The resolution strategies that can be used to
        specify how to resolve conflicts that occur between 
        actions of the same or different policy rules that 
        are matched and contained in this particular NSF";       

      reference
        "draft-ietf-i2nsf-capability-data-model-15:
         I2NSF Capability YANG Data Model - Resolution strategy";
    }
  
    leaf default-action {
      type identityref {
        base default-action;
      }
      default mirror;
      description 
        "This default action can be used to specify a predefined 
        action when no other alternative action was matched 
        by the currently executing I2NSF Policy Rule. An analogy 
        is the use of a default statement in a C switch statement.";
      reference
        "draft-ietf-i2nsf-capability-data-model-15:
         I2NSF Capability YANG Data Model - Default Action";
    }
    
    list rules {
      key "rule-name";
      description
        "This is a rule for network security functions.";
          
      leaf rule-name {
        type string;
        description
          "The name of the rule.";
      }
      
      leaf rule-description {
        type string;
        description
          "This description gives more information about 
           rules.";
      }
  
      leaf rule-priority {
        type uint8 {
          range "1..255";
        }
        description
          "The priority keyword comes with a mandatory 
           numeric value which can range from 1 till 255.
           Note that a higher number means a higher priority";
      }
      
      leaf rule-enable {
        type boolean;
        description
          "True is enable.
           False is not enable.";
      }

      leaf session-aging-time {
        type uint16;
        units "second";
        description
          "This is session aging time.";
      }

      container long-connection {
        description
          "This is long-connection";

        leaf enable {
          type boolean;
          description
            "True is enable.
             False is not enable.";
        }

        leaf duration {
          type uint16;
          description
            "This is the duration of the long-connection.";
        }
      }
      
      container event {
        description 
          "An event is defined as any important 
           occurrence in time of a change in the system being 
           managed, and/or in the environment of the system being 
           managed. When used in the context of policy rules for 
           a flow-based NSF, it is used to determine whether the 
           Condition clause of the Policy Rule can be evaluated 
           or not. Examples of an I2NSF event include time and 
           user actions (e.g., logon, logoff, and actions that 
           violate any ACL.).";
           
        reference
          "RFC 8329: Framework for Interface to Network Security 
           Functions - I2NSF Flow Security Policy Structure
           draft-ietf-i2nsf-capability-data-model-15:
           I2NSF Capability YANG Data Model - Design Principles and
           ECA Policy Model Overview
           draft-ietf-i2nsf-nsf-monitoring-data-model-04: I2NSF
           NSF Monitoring YANG Data Model - Alarms, Events, Logs,
           and Counters";
      
        leaf event-clause-description {
          type string;
          description
            "Description for an event clause";
        }
      
        container event-clauses {
          description
            "System Event Clause - either a system event or
            system alarm";
          reference
            "RFC 8329: Framework for Interface to Network Security 
             Functions - I2NSF Flow Security Policy Structure
             draft-ietf-i2nsf-capability-data-model-15:
             I2NSF Capability YANG Data Model - Design Principles and
             ECA Policy Model Overview
             draft-ietf-i2nsf-nsf-monitoring-data-model-04: I2NSF
             NSF Monitoring YANG Data Model - Alarms, Events, Logs,
             and Counters";
             
          leaf-list system-event {
            type identityref {
              base system-event;
            }
            description
              "The security policy rule according to 
               system events.";
          }
          
          leaf-list system-alarm {
            type identityref {
              base system-alarm;
            }
            description
              "The security policy rule according to 
               system alarms.";
          }
        }
      }
  
      container condition {
        description
          "A condition is defined as a set 
          of attributes, features, and/or values that are to be 
          compared with a set of known attributes, features, 
          and/or values in order to determine whether or not the 
          set of Actions in that (imperative) I2NSF Policy Rule 
          can be executed or not. Examples of I2NSF Conditions
          include matching attributes of a packet or flow, and 
          comparing the internal state of an NSF to a desired 
          state.";
        reference
          "RFC 8329: Framework for Interface to Network Security 
           Functions - I2NSF Flow Security Policy Structure
           draft-ietf-i2nsf-capability-data-model-15:
           I2NSF Capability YANG Data Model - Design Principles and
           ECA Policy Model Overview";

        leaf condition-clause-description {
          type string;
          description
            "Description for a condition clause.";
        }
        
        container mac-condition {
          description
            "The purpose of this container is to represent layer 2 
             packet header information to determine the set of policy 
             actions in this ECA policy rule should be executed or 
             not.";
          reference
            "IEEE 802.3: IEEE Standard for Ethernet";
          
          leaf mac-description {
            type string;
            description
              "The MAC Condition description";
          }
          
          leaf-list source-mac-address {
            type yang:mac-address;
            description
              "The condition for source Media Access Control (MAC)
               Address of a Layer 2 packet. Multiple source MAC 
               Addresses can be given in a single rule.";
            reference
             "IEEE 802.3: IEEE Standard for Ethernet";
          }
          
          leaf-list destination-mac-address {
            type yang:mac-address;
            description
              "The condition for destination Media Access Control (MAC)
               Address of a Layer 2 packet. Multiple destination MAC
               Addresses can be given in a single rule.";
            reference
             "IEEE 802.3: IEEE Standard for Ethernet";
          }
          
          leaf-list ether-type {
            type uint16;
            description
              "The condition for matching the 2-octet of IEEE 802.3
               Length/Type field. Can be specified with decimal or
               hexadecimal from 0 through 65535 (0xFFFF)
               
               A value from 0 through 1500 (0x05DC) specifies the
               number of MAC client data octets contained in the
               subsequent MAC Client Data Field of the basic frame
               
               A value greater than or equal to 1536 (0x0600) specifies
               that the Length/Type field indicates Ethertype of the
               MAC client protocol";
            reference
              "IEEE 802.3: IEEE Standard for Ethernet";
          }        
        }
       
        container ipv4-condition {
          description
            "The purpose of this container is to represent IPv4
             packet header information to determine if the set 
             of policy actions in this ECA policy rule should be 
             executed or not.";
          reference
            "RFC 791: Internet Protocol";
       
          leaf description {
            type string;
            description
             "ipv4 condition textual description.";
          }
          
          container header-length {
            list range-header-length {
              key "start-header-length 
                   end-header-length";
              leaf start-header-length {
                type uint8 {
                  range "5..15";
                }
                description
                  "Starting IPv4 header length for a range match.";
              }
            
              leaf end-header-length {
                type uint8 {
                  range "5..15";
                }
                description
                  "Ending IPv4 header length for a range match.";
              }
              description
                "Range match for an IPv4 header length.";
            }
            description
              "The security policy rule according to 
               IPv4 header length.";
            reference
              "RFC 791: Internet Protocol - Header length";
          }
       
          leaf-list dscp {
            type inet:dscp;
            description
              "The security policy rule according to 
               IPv4 type of service.";
            reference
              "RFC 791: Internet Protocol - Type of service
               RFC 2474: Definition of the Differentiated 
               Services Field (DS Field) in the IPv4 and 
               IPv6 Headers.";
          }
          
          container total-length {
            list range-total-length {
              key "start-total-length end-total-length";
              leaf start-total-length {
                type uint16;
                description
                  "Starting IPv4 total length for a range match.";
              }
              leaf end-total-length {
                type uint16;
                description
                  "Ending IPv4 total length for a range match.";
              }
              description
                "Range match for an IPv4 total length.";
            }
            description
              "The security policy rule according to 
               IPv4 total length.";
            reference
              "RFC 791: Internet Protocol - Total length";
          }
          
          leaf-list identification {
            type uint16;
            description
              "The security policy rule according to 
               IPv4 identification.";
            reference
              "RFC 791: Internet Protocol - Identification";
          }
       
          leaf-list fragment-flags {
            type identityref {
              base fragmentation-flags-type;
            }
            description
              "The security policy rule according to 
               IPv4 fragment flags.";
            reference
              "RFC 791: Internet Protocol - Fragment flags";
          }
       
          container fragment-offset {
            list range-fragment-offset {
              key "start-fragment-offset 
                   end-fragment-offset";
              leaf start-fragment-offset {
                type uint16 {
                  range "0..16383";
                }
                description
                  "Starting IPv4 fragment offset for a range match.";
              }
              leaf end-fragment-offset {
                type uint16 {
                  range "0..16383";
                }
                description
                  "Ending IPv4 fragment offset for a range match.";
              }
              description
                "Range match for an IPv4 fragment offset.";
            }
            description
              "The security policy rule according to 
               IPv4 fragment offset.";
            reference
              "RFC 791: Internet Protocol - Fragment offset";
          }
          
          container ttl {
            list range-ttl {
              key "start-ttl end-ttl";
              leaf start-ttl {
                type uint8;
                description
                  "Starting IPv4 TTL for a range match.";
              }
              leaf end-ttl {
                type uint8;
                description
                  "Ending IPv4 TTL for a range match.";
              }
              description
                "Range match for an IPv4 TTL.";
            }
            description
              "The security policy rule according to 
               IPv4 time-to-live (TTL).";
            reference
              "RFC 791: Internet Protocol - Time to live";
          }
       
       
          leaf-list protocol {
            type identityref {
              base protocol;
            }
            description
              "The security policy rule according to 
               IPv4 protocol.";
            reference
              "RFC 791: Internet Protocol - Protocol";
          }
       
          container source-ip-address {
            uses pkt-sec-ipv4;
            description
              "The security policy rule according to 
               IPv4 source address.";
            reference
              "RFC 791: Internet Protocol - IPv4 Address";
          }
          
          container destination-ip-address {
            uses pkt-sec-ipv4;
            description
              "The security policy rule according to 
               IPv4 destination address.";
            reference
              "RFC 791: Internet Protocol - IPv4 Address";
          }
       
          leaf-list ipopts {
            type identityref {
              base ipopts;
            }
            description
              "The security policy rule according to 
               IPv4 options."; 
            reference
              "RFC 791: Internet Protocol - Options";
          }
       
          leaf same-ip {
            type boolean;
            description
              "Match on packets with the same IPv4 source
               and IPv4 destination address.";
          }
        }
          
        container ipv6-condition {
          description
             "The purpose of this container is to represent 
              IPv6 packet header information to determine 
              if the set of policy actions in this ECA policy 
              rule should be executed or not.";
          reference
             "RFC 8200: Internet Protocol, Version 6 (IPv6) 
              Specification";
       
          leaf description {
            type string;
            description
             "This is description for ipv6 condition.";
          }
          
       
          leaf-list dscp {
            type inet:dscp;
            description
              "The security policy rule according to 
               IPv6 traffic class.";
            reference
              "RFC 8200: Internet Protocol, Version 6 (IPv6) 
               Specification - Traffic class
               RFC 2474: Definition of the Differentiated 
               Services Field (DS Field) in the IPv4 and 
               IPv6 Headers.";
          }
          
          container flow-label {
            list range-flow-label {
              key "start-flow-label end-flow-label";
              leaf start-flow-label {
                type uint32 {
                  range "0..1048575";
                }
                description
                  "Starting IPv6 flow label for a range match.";
              }
              leaf end-flow-label {
                type uint32 {
                  range "0..1048575";
                }
                description
                  "Ending IPv6 flow label for a range match.";
              }
              description
                "Range match for an IPv6 flow label.";
            }
            description
              "The security policy rule according to 
               IPv6 flow label.";
            reference
              "RFC 8200: Internet Protocol, Version 6 (IPv6) 
               Specification - Flow label";
          }
       
          container payload-length {
            list range-payload-length {
              key "start-payload-length 
                   end-payload-length";
              leaf start-payload-length {
                type uint16;
                description
                  "Starting IPv6 payload length for a range match.";
              }
              leaf end-payload-length {
                type uint16;
                description
                  "Ending IPv6 payload length for a range match.";
              }
              description
                "Range match for an IPv6 payload length.";
            }
            description
              "The security policy rule according to 
               IPv6 payload length.";
            reference
              "RFC 8200: Internet Protocol, Version 6 (IPv6) 
               Specification - Payload length";
          }
       
          leaf-list next-header {
            type identityref {
              base next-header;
            }
            description
              "The security policy rule according to 
               IPv6 next header.";
            reference
              "RFC 8200: Internet Protocol, Version 6 (IPv6) 
               Specification - Next header";
          }
          
          container hop-limit {
            list range-hop-limit {
              key "start-hop-limit end-hop-limit";
              leaf start-hop-limit {
                type uint8;
                description
                  "Start IPv6 hop limit for a range match.";
              }
              leaf end-hop-limit {
                type uint8;
                description
                  "End IPv6 hop limit for a range match.";
              }
              description
                "Range match for an IPv6 hop limit.";
            }
            description
              "The security policy rule according to 
               IPv6 hop limit.";
            reference
              "RFC 8200: Internet Protocol, Version 6 (IPv6) 
               Specification - Hop limit";
          }
       
          container source-ip-address {
            uses pkt-sec-ipv6;
            description
              "The security policy rule according to 
               IPv6 source address.";
            reference
              "RFC 8200: Internet Protocol, Version 6 (IPv6) 
               Specification - IPv6 address";
          }
          
          container destination-ip-address {
            uses pkt-sec-ipv6;
            description
              "The security policy rule according to 
               IPv6 destination address.";
            reference
              "RFC 8200: Internet Protocol, Version 6 (IPv6) 
               Specification - IPv6 address";
          }
       
        }
          
        container tcp-condition {
          description
            "The purpose of this container is to represent 
             TCP packet header information to determine 
             if the set of policy actions in this ECA policy 
             rule should be executed or not.";
          reference
            "RFC 793: Transmission Control Protocol";
       
          leaf description {
            type string;
            description
             "This is description for tcp condition.";
          }
          
          container source-port-num {
            uses pkt-sec-port-number;
            description
              "The security policy rule according to 
               tcp source port number.";
            reference
              "RFC 793: Transmission Control Protocol 
               - Port number";
          }
       
          container destination-port-num {
            uses pkt-sec-port-number;
            description
              "The security policy rule according to 
               tcp destination port number.";
            reference
              "RFC 793: Transmission Control Protocol 
               - Port number";
          }
          
          leaf-list flags {
            type identityref {
              base tcp-flags;
            }
            description
              "The security policy rule according to 
               tcp flags.";
            reference
              "RFC 793: Transmission Control Protocol 
               - Flags";
          }
        }
        
        container udp-condition {
          description
            "The purpose of this container is to represent 
             UDP packet header information to determine 
             if the set of policy actions in this ECA policy 
             rule should be executed or not.";
          reference
            "RFC 793: Transmission Control Protocol";
       
          leaf description {
            type string;
            description
             "This is description for udp condition.";
          }
          
          container source-port-num {
            uses pkt-sec-port-number;
            description
              "The security policy rule according to 
               udp source port number.";
            reference
              "RFC 768: User Datagram Protocol 
               - Total Length";
          }
          
          container destination-port-num {
            uses pkt-sec-port-number;
            description
              "The security policy rule according to 
               udp destination port number.";
            reference
              "RFC 768: User Datagram Protocol 
               - Total Length";
          }
          
          container total-length {
            list range-total-length {
              key "start-total-length end-total-length";
              leaf start-total-length {
                type uint32;
                description
                  "Start udp total length for a range match.";
              }
              leaf end-total-length {
                type uint32;
                description
                  "End udp total length for a range match.";
              }
              description
                "Range match for a udp total length.";
            }
            description
              "The security policy rule according to 
               udp total length.";
            reference
              "RFC 768: User Datagram Protocol 
               - Total Length";
          }
        }
        
        container sctp-condition {
          description
            "The purpose of this container is to represent 
             SCTP packet header information to determine 
             if the set of policy actions in this ECA policy 
             rule should be executed or not.";
          leaf description {
            type string;
            description
              "This is description for sctp condition.";
          }
          
          container source-port-num {
            uses pkt-sec-port-number;
            description
              "The security policy rule according to 
               sctp source port number.";
            reference
              "RFC 4960: Stream Control Transmission Protocol
               - Port number";
          }
             
       
          container destination-port-num {
            uses pkt-sec-port-number;
            description
              "The security policy rule according to 
               sctp destination port number.";
            reference
              "RFC 4960: Stream Control Transmission Protocol
               - Total Length";
          }
          
          leaf-list verification-tag {
            type uint32;
            description
              "The security policy rule according to 
               udp total length.";
            reference
              "RFC 4960: Stream Control Transmission Protocol
               - Verification Tag";
          }
          
          leaf-list chunk-type {
            type uint8;
            description
              "The security policy rule according to 
               sctp chunk type ID Value.";
            reference
              "RFC 4960: Stream Control Transmission Protocol
               - Chunk Type";
          }
        }
        
        container dccp-condition {
          description
            "The purpose of this container is to represent 
             DCCP packet header information to determine 
             if the set of policy actions in this ECA policy 
             rule should be executed or not.";
          leaf description {
            type string;
            description
              "This is description for dccp condition.";
          }
          
          container source-port-num {
            uses pkt-sec-port-number;
            description
              "The security policy rule according to 
               dccp source port number.";
            reference
              "RFC 4340: Datagram Congestion Control Protocol (DCCP)
               - Port number";
          }

          container destination-port-num {
            uses pkt-sec-port-number;
            description
              "The security policy rule according to 
               dccp destination port number.";
            reference
              "RFC 4340: Datagram Congestion Control Protocol (DCCP)
               - Port number";
          }
          
          leaf-list service-code {
            type uint32;
            description
              "The security policy rule according to 
               dccp service code.";
            reference
              "RFC 4340: Datagram Congestion Control Protocol (DCCP)
               - Service Codes
               RFC 5595: The Datagram Congestion Control Protocol (DCCP)
               Service Codes
               RFC 6335: Internet Assigned Numbers Authority (IANA)
               Procedures for the Management of the Service Name and
               Transport Protocol Port Number Registry - Service Code";
          }
        }
       
        container icmp-condition {
          description
            "The purpose of this container is to represent 
             ICMP packet header information to determine 
             if the set of policy actions in this ECA policy 
             rule should be executed or not.";
          reference
            "RFC  792: Internet Control Message Protocol
             RFC 8335: PROBE: A Utility for Probing Interfaces";
       
          leaf description {
            type string;
            description
             "This is description for icmp condition.";
          }
          
          leaf-list type-and-code {
            type identityref {
              base icmp-type;
            }
            description
              "The security policy rule according to 
               ICMP parameters.";
            reference
              "RFC  792: Internet Control Message Protocol
               RFC 8335: PROBE: A Utility for Probing Interfaces";
          }
        }

        container url-category-condition {
          description
            "Condition for url category";
          leaf description {
            type string;
            description
              "This is description for the condition of a URL's
               category such as SNS sites, game sites, ecommerce
               sites, company sites, and university sites.";
          }

          leaf-list pre-defined-category {
            type string;
            description
              "This is pre-defined-category.";
          }
          leaf-list user-defined-category {
            type string;
            description
              "This user-defined-category.";
          }
        }
        
        container voice-condition {
          description
            "For the VoIP/VoLTE security system, a VoIP/
             VoLTE security system can monitor each
             VoIP/VoLTE flow and manage VoIP/VoLTE
             security rules controlled by a centralized
             server for VoIP/VoLTE security service
             (called VoIP IPS). The VoIP/VoLTE security
             system controls each switch for the
             VoIP/VoLTE call flow management by
             manipulating the rules that can be added,
             deleted, or modified dynamically.";
          reference
            "RFC 3261: SIP: Session Initiation Protocol";

          leaf description {
            type string;
            description
             "This is description for voice condition.";
          }
          
          leaf-list source-voice-id {
            type string;
            description
              "The security policy rule according to 
               a source voice ID for VoIP and VoLTE.";
          }
          
          leaf-list destination-voice-id {
            type string;
            description
              "The security policy rule according to 
               a destination voice ID for VoIP and VoLTE.";
          }
          
          leaf-list user-agent {
            type string;
            description
              "The security policy rule according to 
               an user agent for VoIP and VoLTE.";
          }
        }
        
        container ddos-condition {
          description
            "Condition for DDoS attack.";

          leaf description {
            type string;
            description
             "This is description for ddos condition.";
          }
          
          leaf alert-packet-rate {
            type uint32;
            units "pps";
            description
              "The alert rate of flood detection for 
               packets per second (PPS) of an IP address.";
          }
          
          leaf alert-flow-rate {
            type uint32;
            description
              "The alert rate of flood detection for 
               flows per second of an IP address.";
          }
          
          leaf alert-byte-rate {
            type uint32;
            units "BPS";
            description
              "The alert rate of flood detection for 
               bytes per second of an IP address.";
          }
        }
        
        container payload-condition {
          description
            "Condition for packet payload";
          leaf packet-payload-description {
            type string;
            description
             "This is description for payload condition.";
          }
          leaf-list payload-content {
            type string;
            description
              "This is a condition for packet payload content.";
          }
        }
        
        container context-condition {
          description
            "Condition for context";
          leaf context-description {
            type string;
            description
              "This is description for context condition.";
          }
          
          container time-condition {
            description
              "Time zone when the rules are applied";
               
            leaf start-date-time {
              type yang:date-and-time;
              description
                "This is the start date and time for a security policy
                 rule.";
            }
            leaf end-date-time {
              type yang:date-and-time;
              description
                "This is the end date and time for a policy rule.  The
                 policy rule will stop working after the specified
                 end-date-time.";
            }
            
            container period{
              when
                "../frequency!='only-once'";
              description
                "This represents the repetition time.  In the case where
                 the frequency is weekly, the days can be set.";
              leaf start-time {
                type time;

                description
                  "This is a period's start time for an event.";		   
              }
              leaf end-time {
                type time;
        
                description
                  "This is a period's end time for an event.";
              }
              leaf-list day {
                when 
                  "../../frequency='weekly'";
                type identityref{
                  base day;
                }
                min-elements 1;
                description
                  "This represents the repeated day of every week (e.g.,
                   Monday and Tuesday).  More than one day can be
                   specified.";
              }
              leaf-list date {
                when 
                  "../../frequency='monthly'";
                type int32{
                  range "1..31";
                }
                min-elements 1;
                description
                  "This represents the repeated date of every month.  More
                   than one date can be specified.";
              }
              leaf-list month {
                when 
                  "../../frequency='yearly'";
                type string{
                  pattern '\d{2}-\d{2}';
                }
                min-elements 1;
                description
                  "This represents the repeated date and month of every
                   year.  More than one can be specified.  A pattern used
                   here is Month and Date (MM-DD).";
              }
            }
            
            leaf frequency {
              type enumeration {
                enum only-once {
                  description
                    "This represents that the rule is immediately enforced
                     only once and not repeated.  The policy will
                     continuously be active from the start-time to the
                     end-time.";
                }
                enum daily {
                  description
                    "This represents that the rule is enforced on a daily
                     basis.  The policy will be repeated daily until the
                     end-date.";
                }
                enum weekly {
                  description
                    "This represents that the rule is enforced on a weekly
                     basis.  The policy will be repeated weekly until the
                     end-date.  The repeated days can be specified.";
                }
                enum monthly {
                  description
                    "This represents that the rule is enforced on a monthly
                     basis. The policy will be repeated monthly until the
                     end-date.";
                }
                enum yearly {
                  description
                    "This represents that the rule is enforced on a yearly
                     basis.  The policy will be repeated yearly until the
                     end-date.";
                }
              }
              default only-once;
              description
                "This represents how frequently the rule should be enforced.";
            }
          }
          
          container application-condition {
            description
              "Condition for application";
            leaf description {
              type string;
              description
               "This is description for application condition.";
            }
            leaf-list object {
              type string;
              description
                "This is application object.";
            }
            leaf-list group {
              type string;
              description
                "This is application group.";
            }
            leaf-list label {
              type string;
              description
                "This is application label.";
            }
            container category {
              description
                "This is application category";
              list application-category {
                key "name subcategory";
                description
                  "This is application category list";

                leaf name {
                  type string;
                  description
                   "This is name for application category.";
                }
                leaf subcategory {
                  type string;
                  description
                   "This is application subcategory.";
                }
              }
            }
          }
          
          container target-condition {
            description
              "Condition for target";
            leaf description {
              type string;
              description
                "This is description for target condition.
                Vendors can write instructions for target condition
                that vendor made";
            }

            leaf-list device {
              type identityref {
                base target-device;
              }
              description
                "The device attribute that can identify a device,
                 including the device type (i.e., router, switch,
                 pc, ios, or android) and the device's owner as
                 well.";
            }
          }
          
          container users-condition {
            description
              "Condition for users";
            leaf users-description {
              type string;
              description
                "This is the description for users' condition.";
            }
            list user{
              key "user-id";
              description
                "The user (or user group) information with which
                 network flow is associated: The user has many
                 attributes such as name, id, password, type,
                 authentication mode and so on. 
                 id is often used in the security policy to
                 identify the user.
                 Besides, an NSF is aware of the IP address of the
                 user provided by a unified user management system
                 via network. Based on name-address association,
                 an NSF is able to enforce the security functions
                 over the given user (or user group)";

              leaf user-id {
                type uint32;
                description
                  "The ID of the user.";
              }
              leaf user-name {
                type string;
                description
                  "The name of the user.";
              }
            }
            list group {
              key "group-id";
              description
                "The user (or user group) information with which
                 network flow is associated: The user has many
                 attributes such as name, id, password, type,
                 authentication mode and so on. 
                 id is often used in the security policy to
                 identify the user.
                 Besides, an NSF is aware of the IP address of the
                 user provided by a unified user management system
                 via network. Based on name-address association,
                 an NSF is able to enforce the security functions
                 over the given user (or user group)";

              leaf group-id {
                type uint32;
                description
                  "The ID of the group.";
              }
              leaf group-name {
                type string;
                description
                  "The name of the group.";
              }
            }
              
            leaf security-group {
              type string;
              description
                "security-group.";
            }
          }
          
          container geography-location-condition {
            description
              "The location which network traffic flow is associated
               with. The region can be the geographical location
               such as country, province, and city,
               as well as the logical network location such as
               IP address, network section, and network domain.";

            leaf description {
              type string;
              description
                "This is description for generic context condition.
                 Vendors can write instructions for generic context
                 condition that vendor made";
            }
            
            leaf-list source {
              type string;
              description
                "The src-geography-location is a geographical 
                 location mapped into an IP address. It matches the
                 mapped IP address to the source IP address of the 
                 traffic flow.";
              reference
                "ISO 3166: Codes for the representation of 
                 names of countries and their subdivisions";
            }
            
            leaf-list destination {
              type string;
              description
                "The dest-geography-location is a geographical 
                 location mapped into an IP address. It matches the 
                 mapped IP address to the destination IP address of 
                 the traffic flow.";
              reference
                "ISO 3166: Codes for the representation of 
                 names of countries and their subdivisions";
            }
          }
        }
      }

      container action {
        description 
          "An action is used to control and monitor aspects of
           flow-based NSFs when the event and condition clauses 
           are satisfied. NSFs provide security functions by 
           executing various Actions. Examples of I2NSF Actions 
           include providing intrusion detection and/or protection, 
           web and flow filtering, and deep packet inspection 
           for packets and flows.";
        reference
          "RFC 8329: Framework for Interface to Network Security 
           Functions - I2NSF Flow Security Policy Structure
           draft-ietf-i2nsf-capability-data-model-15:
           I2NSF Capability YANG Data Model - Design Principles and
           ECA Policy Model Overview";             

        leaf action-clause-description {
          type string;
          description
            "Description for an action clause.";
        }
        
        container packet-action {
          description
            "Action for packets";
          reference
            "RFC 8329: Framework for Interface to Network Security 
             Functions - I2NSF Flow Security Policy Structure
             draft-ietf-i2nsf-capability-data-model-15:
             I2NSF Capability YANG Data Model - Design Principles and
             ECA Policy Model Overview";

          leaf ingress-action {
            type identityref {
              base ingress-action;
            }
            description
              "Ingress Action: pass, drop, reject, rate-limit, and 
               mirror.";
          }
          
          leaf egress-action {
            type identityref {
              base egress-action;
            }
            description
              "Egress action: pass, drop, reject, rate-limit, mirror, 
               invoke-signaling, tunnel-encapsulation, forwarding, 
               and redirection.";
          }

          leaf log-action {
            type identityref {
              base log-action;
            }
            description
              "Log action: rule log and session log";
          }
          
        }  
          
        container flow-action {
          description
            "Action for flows";
          reference
            "RFC 8329: Framework for Interface to Network Security 
             Functions - I2NSF Flow Security Policy Structure
             draft-ietf-i2nsf-capability-data-model-15:
             I2NSF Capability YANG Data Model - Design Principles and
             ECA Policy Model Overview";

          leaf ingress-action {
            type identityref {
              base ingress-action;
            }
            description
              "Action: pass, drop, reject, rate-limit, and mirror.";
          }
          
          leaf egress-action {
            type identityref {
              base egress-action;
            }
            description
              "Egress action: pass, drop, reject, rate-limit, mirror, 
               invoke-signaling, tunnel-encapsulation, forwarding,
               and redirection.";
          }

          leaf log-action {
            type identityref {
              base log-action;
            }
            description
              "Log action: rule log and session log";
          }
        }
        
        container advanced-action {
          description
            "If the packet needs to be additionally inspected, 
             the packet is passed to advanced network 
             security functions according to the profile.
             The profile means the types of NSFs where the packet 
             will be forwarded in order to additionally 
             inspect the packet.";
          reference
            "RFC 8329: Framework for Interface to Network Security 
             Functions - Differences from ACL Data Models";
           
          leaf-list content-security-control {
              type identityref {
                base content-security-control;
              }
              description
                "Content-security-control is the NSFs that 
                 inspect the payload of the packet.
                 The Profile is divided into content security 
                 control and attack-mitigation-control.
                 Content security control: antivirus, ips, ids, 
                 url filtering, mail filtering, file blocking, 
                 file isolate, packet capture, application control, 
                 voip and volte.";
          } 
          
          leaf-list attack-mitigation-control {
              type identityref {
                base attack-mitigation-control;
              }
              description
                "Attack-mitigation-control is the NSFs that weaken 
                 the attacks related to a denial of service 
                 and reconnaissance.
                 The Profile is divided into content security 
                 control and attack-mitigation-control.
                 Attack mitigation control: syn flood, udp flood, 
                 icmp flood, ip frag flood, ipv6 related, http flood, 
                 https flood, dns flood, dns amp flood, ssl ddos, 
                 ip sweep, port scanning, ping of death, teardrop, 
                 oversized icmp, tracert.";
          }
        }        
      }       
    }
    container rule-group {
      description
        "This is rule group";

      list groups {
        key "group-name";
        description
          "This is a group for rules";

        leaf group-name {
          type string;
          description
            "This is a group for rules";
        }

        container rule-range {
          description
            "This is a rule range.";

          leaf start-rule {
            type string;
            description
              "This is a start rule";
          }
          leaf end-rule {
            type string;
            description
              "This is a end rule";
          }
        }
        leaf enable {
          type boolean;
          description
            "This is enable
             False is not enable.";
        }
        leaf description {
          type string;
          description
            "This is a description for rule-group";
        }
      }
    }
  }
}
