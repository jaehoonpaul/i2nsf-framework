module simple {
  namespace "http://tail-f.com/ns/example/simple";
  prefix simple;

  import ietf-inet-types {
    prefix inet;
  }
  import tailf-common {
    prefix tailf;
  }

  /*    A set of server structures  */
  container dp {
    container servers {
      tailf:callpoint simplecp;
      list server {
        key "name number";
        max-elements 64;
        leaf name {
          type string;
        }
        leaf number {
          type int64;
        }
        leaf ip {
          type inet:ip-address;
          mandatory true;
        }
        leaf port {
          type inet:port-number;
          mandatory true;
        }
        leaf obj {
          type instance-identifier {
            require-instance false;
          }
        }
        leaf-list refs {
          type instance-identifier {
            require-instance false;
          }
        }
      }
    }
  }
}
