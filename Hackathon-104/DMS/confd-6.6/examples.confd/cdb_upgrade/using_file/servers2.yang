module servers2 {
  namespace "http://tail-f.com/ns/example/servers";
  prefix servers;

  import ietf-inet-types {
    prefix inet;
  }

  revision 2009-09-01 {
    description
       "Updated version.";
  }
  revision 2009-04-01 {
    description
       "Initial version.";
  }

  container servers {
    list server {
      key name;
      max-elements 64;
      leaf name {
        type string;
      }
      leaf desc {
        type string;
        mandatory true;
      }
      leaf ip {
        type inet:ip-address;
        mandatory true;
      }
      leaf port {
        type inet:port-number;
        mandatory true;
      }
    }
    list interface {
      key name;
      max-elements 64;
      leaf name {
        type string;
      }
      leaf enabled {
        type boolean;
        mandatory true;
      }
      leaf ip {
        type inet:ip-address;
        mandatory true;
      }
    }
  }
}
