module system {
  namespace "http://tail-f.com/ns/system";
  prefix system;

  import ietf-inet-types {
    prefix inet;
  }

  container system {
    container interfaces {
      list interface {
        key name;
        max-elements 64;
        leaf name {
          type string;
        }
        leaf ip {
          type inet:ipv4-address;
          mandatory true;
        }
        leaf enabled {
          type boolean;
          mandatory true;
        }
        leaf mtu {
          type int64;
          default 1500;
        }
        leaf metric {
          type int64;
          mandatory true;
        }
        leaf myflag {
          type empty;
        }
      }
    }
  }
}
