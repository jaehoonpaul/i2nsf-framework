module simple {
  namespace "http://tail-f.com/ns/example/simple";
  prefix simple;

  import tailf-common {
    prefix tailf;
  }

  revision 2009-04-01 {
    description
       "Initial version.";
  }

  typedef myType1 {
    type int32 {
      range "0 .. 7";
    }
  }

  typedef ipv4AddressMask {
    type string;
    tailf:info "IPv4-address/mask-length";
    tailf:typepoint ipv4_mask;
  }

  container simple {
    leaf color {
      type string;
      mandatory true;
    }
    leaf ip {
      type ipv4AddressMask;
    }
    leaf value1 {
      type myType1;
      mandatory true;
    }
    leaf value2 {
      type int16;
      mandatory true;
    }
    leaf value3 {
      type int32;
      mandatory true;
    }
    leaf value4 {
      type int64;
      default 31415926;
    }
    leaf value5 {
      type uint8;
      default 42;
    }
    leaf value6 {
      type int16;
      mandatory true;
    }
    leaf value7 {
      type int32;
    }
    leaf value8 {
      type int8;
    }
    container p {
      presence true;
    }
  }
  container stats {
    config false;
    tailf:cdb-oper {
      tailf:persistent true;
    }
    leaf version {
      type string;
    }
    leaf hardware {
      type string;
    }
    leaf revision {
      type string;
    }
  }
}
