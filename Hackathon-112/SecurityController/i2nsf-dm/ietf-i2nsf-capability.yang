module ietf-i2nsf-capability {
  yang-version 1.1;
  namespace 
    "urn:ietf:params:xml:ns:yang:ietf-i2nsf-capability";
  prefix
    nsfcap;

  organization
    "IETF I2NSF (Interface to Network Security Functions) 
     Working Group";

  contact
    "WG Web: <http://tools.ietf.org/wg/i2nsf>
     WG List: <mailto:i2nsf@ietf.org>

     Editor: Jaehoon Paul Jeong
     <mailto:pauljeong@skku.edu>

     Editor: Jinyong Tim Kim
     <mailto:timkim@skku.edu>

     Editor: Patrick Lingga
     <mailto:patricklink@skku.edu>

     Editor: Susan Hares
     <mailto:shares@ndzh.com>";
     
  description
    "This module is a YANG module for I2NSF Network Security
     Functions (NSFs)'s Capabilities.
	 
     Copyright (c) 2021 IETF Trust and the persons identified as
     authors of the code. All rights reserved.
	 
     Redistribution and use in source and binary forms, with or
     without modification, is permitted pursuant to, and subject to
     the license terms contained in, the Simplified BSD License set
     forth in Section 4.c of the IETF Trust's Legal Provisions
     Relating to IETF Documents
     (https://trustee.ietf.org/license-info).
	 
     This version of this YANG module is part of RFC XXXX
     (https://www.rfc-editor.org/info/rfcXXXX); see the RFC itself
     for full legal notices.";
	 
  // RFC Ed.: replace XXXX with an actual RFC number and remove
  // this note.

  revision "2021-04-30"{
    description "Initial revision.";
    reference
      "RFC XXXX: I2NSF Capability YANG Data Model";

    // RFC Ed.: replace XXXX with an actual RFC number and remove
    // this note.
  }

  /*
   * Identities
   */
  
  identity event {
    description
      "Base identity for I2NSF events.";
    reference
      "draft-ietf-i2nsf-nsf-monitoring-data-model-09: I2NSF NSF
       Monitoring YANG Data Model - Event";
  }
  
  identity system-event {
    base event;
    description 
      "Identity for system event";
    reference
      "draft-ietf-i2nsf-nsf-monitoring-data-model-04: I2NSF NSF
       Monitoring YANG Data Model - System event";	   
  }
  
  identity system-alarm {
    base event;
    description 
      "Identity for system alarm";
    reference
      "draft-ietf-i2nsf-nsf-monitoring-data-model-04: I2NSF NSF
       Monitoring YANG Data Model - System alarm";
  }
  
  identity time {
    base event;
    description
      "Identity for time capabilities";
  }

  identity access-violation {
    base system-event;
    description
      "Identity for access violation event";
    reference
      "draft-ietf-i2nsf-nsf-monitoring-data-model-04: I2NSF NSF
       Monitoring YANG Data Model - System event for access
       violation";
  }
  
  identity configuration-change {
    base system-event;
    description 
      "Identity for configuration change event";
    reference
      "draft-ietf-i2nsf-nsf-monitoring-data-model-04: I2NSF NSF
       Monitoring YANG Data Model - System event for configuration
       change";
  }
  
  identity memory-alarm {
    base system-alarm;
    description
      "Identity for memory alarm. Alarm when memory usage
      exceeds a threshold.";
    reference
      "draft-ietf-i2nsf-nsf-monitoring-data-model-04: I2NSF NSF
       Monitoring YANG Data Model - System alarm for memory";
  }
  
  identity cpu-alarm {
    base system-alarm;
    description
      "Identity for CPU alarm. Alarm when CPU usage 
      exceeds a threshold.";
    reference
      "draft-ietf-i2nsf-nsf-monitoring-data-model-04: I2NSF NSF
       Monitoring YANG Data Model - System alarm for CPU";
  }

  identity disk-alarm {
    base system-alarm;
    description 
      "Identity for disk alarm. Alarm when disk usage 
      exceeds a threshold.";
    reference
      "draft-ietf-i2nsf-nsf-monitoring-data-model-04: I2NSF NSF
       Monitoring YANG Data Model - System alarm for disk";
  }

  identity hardware-alarm {
    base system-alarm;
    description 
      "Identity for hardware alarm. Alarm when a hardware failure
      or hardware degradation occurs.";
    reference
      "draft-ietf-i2nsf-nsf-monitoring-data-model-04: I2NSF NSF
       Monitoring YANG Data Model - System alarm for hardware";
  }

  identity interface-alarm {
    base system-alarm;
    description 
      "Identity for interface alarm. Alarm when interface usage 
      exceeds a threshold.";
    reference
      "draft-ietf-i2nsf-nsf-monitoring-data-model-04: I2NSF NSF
       Monitoring YANG Data Model - System alarm for interface";
  }
  
  identity absolute-time {
    base time;
    description
      "absolute time capabilities. 
       If a network security function has the absolute time 
       capability, the network security function supports
       rule execution according to absolute time.";
  }

  identity periodic-time {
    base time;
    description
      "periodic time capabilities. 
       If a network security function has the periodic time 
       capability, the network security function supports
       rule execution according to periodic time.";
  }
  
  identity target-device {
    description 
      "Identity for target condition capability";
    reference
      "RFC 8519: YANG Data Model for Network Access Control Lists
       (ACLs) - An access control for a target (e.g., the 
       corresponding IP address) in an NSF.";
  }
  
  identity computer {
    base target-device;
    description 
      "Identity for computer such as personal computer (PC)
       and server";
  }
  
  identity mobile-phone {
    base target-device;
    description 
      "Identity for mobile-phone such as smartphone and
       cellphone";
  }
  
  identity voip-volte-phone {
    base target-device;
    description 
      "Identity for voip-volte-phone";
  }
  
  identity tablet {
    base target-device;
    description 
      "Identity for tablet";
  }
  
  identity network-infrastructure-device {
    base target-device;
    description 
      "Identity for network infrastructure devices
       such as switch, router, and access point";
  }
  
  identity iot {
    base target-device;
    description 
      "Identity for IoT (Internet of Things)";
  }
  
  identity vehicle {
    base target-device;
    description 
      "Identity for vehicle that connects to and shares
       data through the Internet";
  }
  
  identity user-condition {
    description
      "Base identity for user condition capability. This is the
       capability of mapping user(s) into their corresponding IP
       address";
  }
  
  identity user {
    base user-condition;
    description 
      "Identity for user condition capability.
       A user (e.g., employee) can be mapped to an IP address of 
       a computing device (e.g., computer, laptop, and virtual
       machine) which the user is using.";
  }
  
  identity group {
    base user-condition;
    description 
      "Identity for group condition capability.
       A group (e.g., employees) can be mapped to multiple IP
       addresses of computing devices (e.g., computers, laptops,
       and virtual machines) which the group is using."; 
  }
  
  identity geography-location {
    description 
      "Identity for geography condition capability";
    reference
      "RFC 8805: A Format for Self-Published IP Geolocation Feeds -
       An access control for a geographical location (i.e., 
       geolocation) that has the corresponding IP prefix.";
  }
  
  identity source-location {
    base geography-location;
    description 
      "Identity for source geography location condition capability";
    reference
      "RFC 8805: A Format for Self-Published IP Geolocation Feeds -
       An access control for a geographical location (i.e., 
       geolocation) that has the corresponding IP prefix.";
  }
  
  identity destination-location {
    base geography-location;
    description 
      "Identity for destination geography location condition
       capability";
    reference
      "RFC 8805: A Format for Self-Published IP Geolocation Feeds -
       An access control for a geographical location (i.e., 
       geolocation) that has the corresponding IP prefix.";
  }
  
  identity directional {
    description
      "Base identity for directional traffic flow capability";
    reference
      "RFC 5101: Specification of the IP Flow Information
       Export (IPFIX) Protocol for the Exchange of IP 
       Traffic Flow Information - Terminology Unidirectional
       and Bidirectional Flow";
  }
  
  identity unidirectional {
    base directional;
    description
      "Identity for unirectional traffic flow.";
    reference
      "RFC 5101: Specification of the IP Flow Information
       Export (IPFIX) Protocol for the Exchange of IP 
       Traffic Flow Information - Terminology Unidirectional
       Flow";
  }
  
  identity bidirectional {
    base directional;
    description
      "Identity for bidirectional traffic flow.";
    reference
      "RFC 5101: Specification of the IP Flow Information
       Export (IPFIX) Protocol for the Exchange of IP 
       Traffic Flow Information - Terminology Bidirectional
       Flow";
  }
  
  identity protocol {
    description
      "Base identity for Internet Protocols";
  }
    
  identity ip {
    base protocol;
    description
      "Base identity for internet/network layer protocol, 
      e.g., IPv4, IPv6, and ICMP.";
  }
  
  identity ipv4 {
    base ip;
    description 
      "Base identity for IPv4 condition capability";
    reference
      "RFC 791: Internet Protocol";
  }
  
  identity ipv6 {
    base ip;
    description
      "Base identity for IPv6 condition capabilities";
    reference
      "RFC 8200: Internet Protocol, Version 6 (IPv6) 
      Specification";
  }
  
  identity icmp {
    base ip;
    description
      "Base identity for ICMPv4 and ICMPv6 condition capability";
    reference
      "RFC 792: Internet Control Message Protocol
       RFC 4443: Internet Control Message Protocol (ICMPv6)
       for the Internet Protocol Version 6 (IPv6) Specification
       - ICMPv6";
  }
   
  identity dscp {
    base ipv4;
    base ipv6;
    description 
      "Identity for the capability of matching IPv4 annd IPv6 
       Differentiated Services Codepoint (DSCP) condition";
    reference
      "RFC 791: Internet Protocol - Type of Service
       RFC 2474: Definition of the Differentiated 
       Services Field (DS Field) in the IPv4 and 
	     IPv6 Headers
       RFC 8200: Internet Protocol, Version 6 (IPv6) 
       Specification - Traffic Class";
  }
  
  identity length {
    base ipv4;
    base ipv6;
    description 
      "Identity for the capability of matching IPv4 Total Length header
       field or IPv6 Payload Length header field.
       
       IPv4 Total Length is the length of datagram, measured in octets,
       including internet header and data.
       
       IPv6 Payload Length is the length of the IPv6 payload, i.e., the
       rest of the packet following the IPv6 header, measured in 
       octets.";
    reference
      "RFC 791: Internet Protocol - Total Length
       RFC 8200: Internet Protocol, Version 6 (IPv6) 
       Specification - Payload Length";
  }
  
  identity ttl {
    base ipv4;
    base ipv6;
    description 
      "Identity for the capability of matching IPv4 Time-To-Live (TTL)
       or IPv6 Hop Limit.";
    reference
      "RFC 791: Internet Protocol - Time To Live (TTL)
       RFC 8200: Internet Protocol, Version 6 (IPv6) 
       Specification - Hop Limit";
  }
  
  identity next-header {
    base ipv4;
    base ipv6;
    description 
      "Identity for the capability of matching IPv4 Protocol Field or
       equivalent to IPv6 Next Header.";
    reference
      "IANA Website: Assigned Internet Protocol Numbers
       - Protocol Number for IPv4
       RFC 791: Internet Protocol - Protocol
       RFC 8200: Internet Protocol, Version 6 (IPv6) 
       Specification - Next Header";
  }
  
  identity source-address {
    base ipv4;
    base ipv6;
    description
      "Identity for the capability of matching IPv4 or IPv6 source 
       address(es) condition capability. The addresses are specified 
       by a pair of by a start address and an end address.";
    reference
      "RFC 791: Internet Protocol - Address
       RFC 8200: Internet Protocol, Version 6 (IPv6) 
       Specification - Source Address";
  }

  identity destination-address {
    base ipv4;
    base ipv6;
    description
      "Identity for the capability of matching IPv4 or IPv6 destination
       address(es) condition capability. The addresses are specified
       by a pair of by a start address and an end address.";
    reference
      "RFC 791: Internet Protocol - Address
       RFC 8200: Internet Protocol, Version 6 (IPv6) 
       Specification - Destination Address";
  }
  
  identity flow-direction {
    base ipv4;
    base ipv6;
    description
      "Identity for flow direction of matching IPv4 source
       or destination address(es) condition capability where flow
       direction is either unidirectional or bidirectional";
    reference
      "RFC 4340: Datagram Congestion Control Protocol";
  }

  identity header-length {
    base ipv4;
    description 
      "Identity for match IPv4 header-length
      condition capability";
    reference
      "RFC 791: Internet Protocol - Header Length";
  }
  
  identity identification {
    base ipv4;
    description 
      "Identity for IPv4 identification condition capability.
       IPv4 ID field is used for fragmentation and reassembly.";
    reference
      "RFC 791: Internet Protocol - Identification
       RFC 6864: Updated Specification of the IPv4 ID Field -
       Fragmentation and Reassembly";
  }
  
  identity fragment-flags {
    base ipv4;
    description 
      "Identity for IPv4 fragment flags condition capability";
    reference
      "RFC 791: Internet Protocol - Fragmentation Flags";
  }
  
  identity fragment-offset {
    base ipv4;
    description 
      "Identity for match IPv4 fragment offset
      condition capability";
    reference
      "RFC 791: Internet Protocol - Fragmentation Offset";
  }
    
  identity ipv4-options {
    base ipv4;
    description
      "Identity for IPv4 options condition capability";
    reference
      "RFC 791: Internet Protocol - Options";
  }
  
  identity flow-label {
    base ipv6;
    description
      "Identity for match IPv6 flow label
      condition capability";
    reference
      "RFC 8200: Internet Protocol, Version 6 (IPv6) 
       Specification - Flow Label
       RFC 6437: IPv6 Flow Label Specification";
  }
  
  identity header-order {
    base ipv6;
    description
      "Identity for IPv6 extension header order condition
      capability";
    reference
      "RFC 8200: Internet Protocol, Version 6 (IPv6) 
       Specification - Extension Header Order";
  }
  
  identity hop-by-hop {
    base ipv6;
    description
      "Identity for IPv6 hop by hop options header 
      condition capability";
    reference
      "RFC 8200: Internet Protocol, Version 6 (IPv6) 
      
      Specification - Options";
  }
  
  identity routing-header {
    base ipv6;
    description
      "Identity for IPv6 routing header condition
      capability";
    reference
      "RFC 8200: Internet Protocol, Version 6 (IPv6) 
      Specification - Routing Header";
  }
  
  identity fragment-header {
    base ipv6;
    description
      "Identity for IPv6 fragment header condition
      capability";
    reference
      "RFC 8200: Internet Protocol, Version 6 (IPv6) 
      Specification - Fragment Header";
  }
  
  identity destination-options {
    base ipv6;
    description
      "Identity for IPv6 destination options condition
      capability";
    reference
      "RFC 8200: Internet Protocol, Version 6 (IPv6) 
      Specification - Destination Options";
  }
  
  identity icmpv4 {
    base icmp;
    description
      "Base identity for ICMPv4 condition capability";
    reference
      "RFC 792: Internet Control Message Protocol";
  }

  identity icmpv6 {
    base icmp;
    description
      "Base identity for ICMPv6 condition capability";
    reference
      "RFC 4443: Internet Control Message Protocol (ICMPv6)
       for the Internet Protocol Version 6 (IPv6) Specification
       - ICMPv6";
  }

  identity type {
    base icmpv4;
    base icmpv6;
    description
      "Identity for ICMPv4 and ICMPv6 type condition capability";
    reference
      "RFC 792: Internet Control Message Protocol
       RFC 4443: Internet Control Message Protocol (ICMPv6)
       for the Internet Protocol Version 6 (IPv6) Specification
       - ICMPv6";
  }

  identity code {
    base icmpv4;
    base icmpv6;
    description
      "Identity for ICMPv4 and ICMPv6 code condition capability";
    reference
      "RFC 792: Internet Control Message Protocol
       RFC 4443: Internet Control Message Protocol (ICMPv6)
       for the Internet Protocol Version 6 (IPv6) Specification
       - ICMPv6";
  }
  
  identity transport-protocol {
    base protocol;
    description
      "Base identity for Layer 4 protocol condition capabilities, e.g.,
       TCP, UDP, SCTP, DCCP, and ICMP";
  }
  
  identity tcp {
    base transport-protocol;
    description
      "Base identity for TCP condition capabilities";
    reference
      "RFC 793: Transmission Control Protocol
       draft-ietf-tcpm-rfc793bis: Transmission Control Protocol 
       (TCP) Specification";
  }
  
  identity udp {
    base transport-protocol;
    description
      "Base identity for UDP condition capabilities";
    reference
      "RFC 768: User Datagram Protocol";
  }

  identity sctp {
    base transport-protocol;
    description
      "Identity for SCTP condition capabilities";
    reference
      "RFC 4960: Stream Control Transmission Protocol";
  }

  identity dccp {
    base transport-protocol;
    description
      "Identity for DCCP condition capabilities";
    reference
      "RFC 4340: Datagram Congestion Control Protocol";
  }
  
  identity source-port-number {
    base tcp;
    base udp;
    base sctp;
    base dccp;
    description
      "Identity for match TCP, UDP, SCTP, and DCCP source port 
       number condition capability";
    reference
      "RFC 793: Transmission Control Protocol - Port Number
       draft-ietf-tcpm-rfc793bis: Transmission Control Protocol 
       (TCP) Specification
       RFC 768: User Datagram Protocol
       RFC 4960: Stream Control Transmission Protocol
       RFC 4340: Datagram Congestion Control Protocol";
  }
  
  identity destination-port-number {
    base tcp;
    base udp;
    base sctp;
    base dccp;
    description
      "Identity for match TCP, UDP, SCTP, and DCCP destination port 
       number condition capability";
    reference
      "RFC 793: Transmission Control Protocol - Port Number
       draft-ietf-tcpm-rfc793bis: Transmission Control Protocol 
       (TCP) Specification";
  }

  identity flags {
    base tcp;
    description
      "Identity for TCP control bits (flags) condition capability";
    reference
      "RFC 793: Transmission Control Protocol - Flags
       RFC 3168: The Addition of Explicit Congestion Notification 
       (ECN) to IP - TCP Header Flags
       draft-ietf-tcpm-rfc793bis: Transmission Control Protocol 
       (TCP) Specification
       draft-ietf-tcpm-accurate-ecn: More Accurate ECN Feedback 
       in TCP";
  }
  
  identity tcp-options {
    base tcp;
    description
      "Identity for TCP options condition capability.";
    reference
      "RFC 793: Transmission Control Protocol - Options
       draft-ietf-tcpm-rfc793bis: Transmission Control Protocol 
       (TCP) Specification
       RFC 6691: TCP Options and Maximum Segment Size
       RFC 7323: TCP Extensions for High Performance";
  }
  
  identity total-length {
    base udp;
    description
      "Identity for match UDP total-length condition capability.
       The UDP total length can be smaller than the IP transport
       length for UDP transport layer options.";
    reference
      "RFC 768: User Datagram Protocol - Total Length
       draft-ietf-tsvwg-udp-options: Transport Options for UDP";
  }

  identity verification-tag {
    base sctp;
    description
      "Identity for range-match SCTP verification tag condition
       capability";
    reference
      "RFC 4960: Stream Control Transmission Protocol - Verification 
       Tag";
  }
  
  identity chunk-type {
    base sctp;
    description
      "Identity for SCTP chunk type condition capability";
    reference
      "RFC 4960: Stream Control Transmission Protocol - Chunk Type";
  }
  
  identity service-code {
    base dccp;
    description
      "Identity for DCCP Service Code condition capabilitiy";
    reference
      "RFC 4340: Datagram Congestion Control Protocol
       RFC 5595: The Datagram Congestion Control Protocol (DCCP) 
       Service Codes
       RFC 6335: Internet Assigned Numbers Authority (IANA) 
       Procedures for the Management of the Service Name and
       Transport Protocol Port Number Registry - Service Code";
  }
  
  identity application-protocol {
    base protocol;
    description
      "Base identity for Application protocol";
  }
  
  identity http {
    base application-protocol;
    description
      "HTTP protocol type.";
    reference
      "RFC 2616: Hypertext Transfer Protocol (HTTP)
       RFC7230: Hypertext Transfer Protocol (HTTP/1.1): Message
       Syntax and Routing
       RFC7231: Hypertext Transfer Protocol (HTTP/1.1): Semantics
       and Content";
  }
  
  identity https {
    base application-protocol;
    description
      "HTTPS protocol type.";
    reference
      "RFC 2818: HTTP over TLS (HTTPS)
       RFC7230: Hypertext Transfer Protocol (HTTP/1.1): Message
       Syntax and Routing
       RFC7231: Hypertext Transfer Protocol (HTTP/1.1): Semantics
       and Content";
  }

  identity ftp {
    base application-protocol;
    description
      "The identity for ftp protocol.";
    reference
      "RFC 959: File Transfer Protocol (FTP)";
  }

  identity ssh {
    base application-protocol;
    description
      "The identity for ssh protocol.";
    reference
      "RFC 4250: The Secure Shell (SSH) Protocol";
  }

  identity telnet {
    base application-protocol;
    description
      "The identity for telnet.";
    reference
      "RFC 854: Telnet Protocol";
  }

  identity smtp {
    base application-protocol;
    description
      "The identity for smtp.";
    reference
      "RFC 5321: Simple Mail Transfer Protocol (SMTP)";
  }

  identity sftp {
    base application-protocol;
    description
      "The identity for sftp.";
    reference
      "RFC 913: Simple File Transfer Protocol (SFTP)";
  }

  identity pop3 {
    base application-protocol;
    description
      "The identity for pop3.";
    reference
      "RFC 1081: Post Office Protocol -Version 3 (POP3)";
  }
    
  identity action {
    description
      "Base identity for action capability";
  }
 
  identity log-action {
    base action;
    description
      "Base identity for log-action capability";
  }
  
  identity ingress-action {
    base action;
    description
      "Base identity for ingress-action capability";
    reference
      "RFC 8329: Framework for Interface to Network Security
       Functions - Ingress action";
  }   
  
  identity egress-action {
    base action;
    description
      "Base identity for egress-action capability";
    reference
      "RFC 8329: Framework for Interface to Network Security
       Functions - Egress action";
  }
  
  identity default-action {
    base action;
    description
      "Base identity for default-action capability";
  }    
 
  identity rule-log {
    base log-action;
    description
      "Identity for rule log log-action capability.
       Log the received packet based on the rule";
  }  
  
  identity session-log {
    base log-action;
    description
      "Identity for session log log-action capability.
       Log the received packet based on the session.";
  }
  

  identity pass {
    base ingress-action;
    base egress-action;
    base default-action;
    description
      "Identity for pass action capability";
    reference
      "RFC 8329: Framework for Interface to Network Security
       Functions - Ingress, egress, and pass actions.";
  }
  
  identity drop {
    base ingress-action;
    base egress-action;
    base default-action;
    description
      "Identity for drop action capability";
    reference
      "RFC 8329: Framework for Interface to Network Security
       Functions - Ingress, egress, and drop actions.";
  }

  identity mirror {
    base ingress-action;
    base egress-action;
    base default-action;
    description
      "Identity for mirror action capability.";
    reference
      "RFC 8329: Framework for Interface to Network Security
       Functions - Ingress, egress, and mirror actions.";
  } 
  
  identity rate-limit {
    base ingress-action;
    base egress-action;
    base default-action;
    description
      "Identity for rate limiting action capability.";
    reference
      "RFC 8329: Framework for Interface to Network Security
       Functions - Ingress, egress, and rate limiting actions.";
  }
  
  identity invoke-signaling {
    base egress-action;
    description
      "Identity for invoke signaling action capability";
    reference
      "RFC 8329: Framework for Interface to Network Security
       Functions - Invoke-signaling action";
  }
  
  identity tunnel-encapsulation {
    base egress-action;
    description
      "Identity for tunnel encapsulation action capability";
    reference
      "RFC 8329: Framework for Interface to Network Security
       Functions - Tunnel Encapsulation";	  
  }
  
  identity forwarding {
    base egress-action;
    description
      "Identity for forwarding action capability";
    reference
      "RFC 8329: Framework for Interface to Network Security
       Functions - Forwarding action";	  
  }
  
  identity transformation {
    base egress-action;
    description
      "Identity for transformation action capability";
    reference
      "RFC 8329: Framework for Interface to Network Security
       Functions - Redirection action";	  
  }
  
  identity resolution-strategy {
    description 
      "Base identity for resolution strategy capability";
  }
  
  identity fmr {
    base resolution-strategy;
    description 
      "Identity for First Matching Rule (FMR) resolution
       strategy capability";
  }

  identity lmr {
    base resolution-strategy;
    description 
      "Identity for Last Matching Rule (LMR) resolution
       strategy capability";
  }
  
  identity pmr {
    base resolution-strategy;
    description 
      "Identity for Prioritized Matching Rule (PMR) resolution
       strategy capability";
  }
  
  identity pmre {
    base resolution-strategy;
    description 
      "Identity for Prioritized Matching Rule with Errors (PMRE)
       resolution strategy capability";
  }
  
  identity pmrn {
    base resolution-strategy;
    description 
      "Identity for Prioritized Matching Rule with No Errors (PMRN)
       resolution strategy capability";
  }
  
  identity advanced-nsf {
    description 
      "Base identity for advanced Network Security Function (NSF)
       capability.  This can be used for advanced NSFs such as
       Anti-DDoS Attack, IPS, URL-Filtering
       and VoIP/VoLTE Filter.";
  }
  
  identity content-security-control {
    base advanced-nsf;
    description
      "Base identity for content security control";
    reference
      "RFC 8329: Framework for Interface to 
       Network Security Functions - Flow-Based 
       NSF Capability Characterization";
  }
  
  identity attack-mitigation-control {
    base advanced-nsf;
    description
      "Base identity for attack mitigation control";
    reference
      "RFC 8329: Framework for Interface to 
       Network Security Functions - Flow-Based 
       NSF Capability Characterization";
  }

  identity ips {
    base content-security-control;
    description
      "Identity for advanced NSF IPS capabilities.  This can be
       used for an extension point for IPS as an advanced NSF.";
  }   
  
  identity url-filtering {
    base content-security-control;
    description
      "Base identity for URL condition capability";
  }

  identity voip-volte-filtering {
    base content-security-control;
    description
      "Identity for advanced NSF VoIP/VoLTE Security Service
       capability.  This can be used for an extension point
       for VoIP/VoLTE Security Service as an advanced NSF.";
    reference
      "RFC 3261: SIP: Session Initiation Protocol";
  }
  
  identity anti-ddos {
    base attack-mitigation-control;
    description
      "Identity for advanced NSF Anti-DDoS Attack or DDoS Mitigator
       capability.  This can be used for an extension point for 
       Anti-DDoS Attack as an advanced NSF.";
  }
    
  identity packet-rate {
    base anti-ddos;
    description
      "Identity for advanced NSF Anti-DDoS detecting Packet Rate
       capability.  The NSF with this capability can detect the 
       incoming packet rate and create an alert if the rate exceeds
       the threshold.";
  }
  
  identity flow-rate {
    base anti-ddos;
    description
      "Identity for advanced NSF Anti-DDoS detecting Flow Rate
       capability.  The NSF with this capability can detect the 
       incoming flow rate and create an alert if the rate exceeds
       the threshold.";   
  }
  
  identity byte-rate {
    base anti-ddos;
    description
      "Identity for advanced NSF Anti-DDoS detecting Byte Rate
       capability.  The NSF with this capability can detect the 
       incoming byte rate and create an alert if the rate exceeds
       the threshold.";
  }

  identity signature-set {
    base ips;
    description
      "Identity for advanced NSF IPS Signature Set capability.
       This can be used for an extension point for IPS Signature
       Set as an advanced NSF.";
    reference
      "RFC 8329: Framework for Interface to Network Security
       Functions - Advanced NSF IPS Signature Set capability";
  }

  identity ips-exception-signature {
    base ips;
    description
      "Identity for advanced NSF IPS Exception Signature
       capability.  This can be used for an extension point for
       IPS Exception Signature as an advanced NSF.";
    reference
      "RFC 8329: Framework for Interface to Network Security
       Functions - Advanced NSF IPS Exception Signature Set
       capability";
  }
  
  identity pre-defined {
    base url-filtering;
    description
      "Identity for pre-defined URL Database condition capability.
       where URL database is a public database for URL filtering.";
  }
  
  identity user-defined {
    base url-filtering;
    description
      "Identity for user-defined URL Database condition capability.
       that allows a users manual addition of URLs for URL
       filtering.";
  }
  
  identity call-id {
    base voip-volte-filtering;
    description
      "Identity for advanced NSF VoIP/VoLTE Call Identifier (ID)
       capability.  This can be used for an extension point for
       VoIP/VoLTE Call ID as an advanced NSF.";
    reference
      "RFC 3261: SIP: Session Initiation Protocol";
  }
  
  identity user-agent {
    base voip-volte-filtering;
    description
      "Identity for advanced NSF VoIP/VoLTE User Agent capability.
       This can be used for an extension point for VoIP/VoLTE
       User Agent as an advanced NSF.";
    reference
      "RFC 3261: SIP: Session Initiation Protocol";
  }
  
  /*
   *  Grouping
   */
  
  grouping nsf-capabilities {
    description
      "Network Security Function (NSF) Capabilities"; 
    reference
      "RFC 8329: Framework for Interface to Network Security 
       Functions - I2NSF Flow Security Policy Structure.";
       
    leaf-list directional-capabilities {
      type identityref {
        base directional;
      }
      description
        "The capability of an NSF for handling directional traffic
        flow (i.e., unidirectional or bidirectional traffic flow).";
    }
   
    container event-capabilities {
      description
        "Capabilities of events.
         If a network security function has the event capabilities,
         the network security function supports rule execution
         according to system event and system alarm.";
       
      reference
        "RFC 8329: Framework for Interface to Network Security 
         Functions - I2NSF Flow Security Policy Structure.
         draft-ietf-i2nsf-nsf-monitoring-data-model-04: I2NSF
         NSF Monitoring YANG Data Model - System Alarm and
         System Events.";
       
      leaf-list system-event-capability {
        type identityref {
          base system-event;
        }
        description
          "System event capabilities";
      }
    
      leaf-list system-alarm-capability {
        type identityref {
          base system-alarm;
        }
        description
          "System alarm capabilities";
      }
      
      leaf-list time-capabilities {
        type identityref {
          base time;
        }
        description
          "The capabilities for activating the policy within a specific
           time."; 
      }
    }
    
    container condition-capabilities {
      description 
        "Conditions capabilities.";
      container generic-nsf-capabilities {
        description 
          "Conditions capabilities. 
           If a network security function has the condition
           capabilities, the network security function
           supports rule execution according to conditions of
           IPv4, IPv6, TCP, UDP, SCTP, DCCP, ICMP, or ICMPv6.";
        reference
          "RFC 768: User Datagram Protocol - UDP.
           RFC 791: Internet Protocol - IPv4.
           RFC 792: Internet Control Message Protocol - ICMP.
           RFC 793: Transmission Control Protocol - TCP.
           RFC 4443: Internet Control Message Protocol (ICMPv6)
           for the Internet Protocol Version 6 (IPv6) Specification
           - ICMPv6.
           RFC 4960: Stream Control Transmission Protocol - SCTP.
           RFC 8200: Internet Protocol, Version 6 (IPv6) 
           Specification - IPv6.
           RFC 8329: Framework for Interface to Network Security
           Functions - I2NSF Flow Security Policy Structure.";
         
        leaf-list ipv4-capability {
          type identityref {
            base ipv4;
          }
          description
            "IPv4 packet capabilities";
          reference
            "RFC 791: Internet Protocol";
        }

        leaf-list ipv6-capability {
          type identityref {
            base ipv6;
          }
          description
            "IPv6 packet capabilities";
          reference
            "RFC 8200: Internet Protocol, Version 6 (IPv6) 
             Specification - IPv6";
        }

        leaf-list icmpv4-capability {
          type identityref {
            base icmpv4;
          }
          description
            "ICMPv4 packet capabilities";
          reference
            "RFC 792: Internet Control Message Protocol - ICMP";
        }
        
        leaf-list icmpv6-capability {
          type identityref {
            base icmpv6;
          }
          description
            "ICMPv6 packet capabilities";
          reference
            "RFC 4443: Internet Control Message Protocol (ICMPv6)
             for the Internet Protocol Version 6 (IPv6) Specification
             - ICMPv6";
        }

        leaf-list tcp-capability {
          type identityref {
            base tcp;
          }
          description
            "TCP packet capabilities";
          reference
            "RFC 793: Transmission Control Protocol - TCP
             draft-ietf-tcpm-rfc793bis-19: Transmission Control Protocol 
             (TCP) Specification";
        }

        leaf-list udp-capability {
          type identityref {
            base udp;
          }
          description
            "UDP packet capabilities";
          reference
            "RFC 768: User Datagram Protocol - UDP";
        }		
        
        leaf-list sctp-capability {
          type identityref {
            base sctp;
          }
          description
            "SCTP packet capabilities";
          reference
            "RFC 4960: Stream Control Transmission Protocol - SCTP";
        }
        
        leaf-list dccp-capability {
          type identityref {
            base dccp;
          }
          description
            "DCCP packet capabilities";
          reference
            "RFC 4340: Datagram Congestion Control Protocol - DCCP";
        }
      }
      
      container advanced-nsf-capabilities {
        description 
          "Advanced Network Security Function (NSF) capabilities, 
           such as Anti-DDoS, IPS, and VoIP/VoLTE.
           This container contains the leaf-lists of advanced
           NSF capabilities";
        reference
          "RFC 8329: Framework for Interface to Network Security 
           Functions - Advanced NSF capabilities";
        
        leaf-list anti-ddos-capability {
          type identityref {
            base anti-ddos;
          }
          description
            "Anti-DDoS Attack capabilities";
          reference
            "RFC 8329: Framework for Interface to Network Security 
             Functions - Advanced NSF Anti-DDoS Attack capabilities";			 
        }
        
        leaf-list ips-capability {
          type identityref {
            base ips;
          }
          description
            "IPS capabilities";
          reference
            "RFC 8329: Framework for Interface to Network Security
             Functions - Advanced NSF IPS capabilities";		  
        }
      
        leaf-list url-capability {
          type identityref {
            base url-filtering;
          }
          description
            "URL capabilities";
          reference
            "RFC 8329: Framework for Interface to Network Security
             Functions - Advanced NSF URL capabilities";		  
        }
        
        leaf-list voip-volte-filtering-capability {
          type identityref {
            base voip-volte-filtering;
         }
          description
            "VoIP/VoLTE capabilities";
          reference
            "RFC 8329: Framework for Interface to Network Security
             Functions - Advanced NSF VoIP/VoLTE capabilities";		  
        }    
      }
              
      container context-capabilities {
        description
          "Security context capabilities";
        leaf-list application-filter-capabilities{
          type identityref {
            base application-protocol;
          }
          description
            "Context capabilities based on the application protocol";
        }
        
        leaf-list target-capabilities {
          type identityref {
            base target-device;
          }
          description
            "Context capabilities based on the device attribute that 
            can identify a device type 
            (i.e., router, switch, pc, ios, or android).";
        }
        
        leaf-list user-condition-capabilities {
          type identityref {
            base user-condition;
          }
          description
            "Context capabilities based on user condition, such as
             user-id or user-name. The users can collected into a 
             user-group and identified with group-id or group-name.
             An NSF is aware of the IP address of the user provided by 
             a unified user management system via network. Based on 
             name-address association, an NSF is able to enforce the
             security functions over the given user (or user group)";
        }
        
        leaf-list geography-capabilities {
          type identityref {
            base geography-location;
          }
          description
            "Context condition capabilities based on the geographical
             location of the source or destination";
        }
      }
    }

    container action-capabilities {     
      description 
        "Action capabilities. 
         If a network security function has the action capabilities,
         the network security function supports the attendant
         actions for policy rules.";
       
      leaf-list ingress-action-capability {
        type identityref {
          base ingress-action;
        }
        description
          "Ingress-action capabilities";
      }
    
      leaf-list egress-action-capability {
        type identityref {
          base egress-action;
        }
        description
          "Egress-action capabilities";
      }
    
      leaf-list log-action-capability {
        type identityref {
          base log-action;
        }
        description
          "Log-action capabilities";
      }
    } 
    
    leaf-list resolution-strategy-capabilities {
      type identityref {
        base resolution-strategy;
      }
      description 
        "Resolution strategy capabilities.
         The resolution strategies can be used to specify how
         to resolve conflicts that occur between the actions
         of the same or different policy rules that are matched
         for the same packet and by particular NSF."; 
    }
    
    leaf-list default-action-capabilities {
      type identityref {
        base default-action;
      }
      description
        "Default action capabilities.
         A default action is used to execute I2NSF policy rules
         when no rule matches a packet. The default action is 
         defined as pass, drop, rate-limit, or mirror.";
      reference
        "RFC 8329: Framework for Interface to Network Security
         Functions - Ingress and egress actions.";
    }
  }
    
  /*
   * Data nodes
   */
   
  list nsf {
    key "nsf-name";
    description
      "The list of Network Security Functions (NSFs)";
    leaf nsf-name {
      type string;
      mandatory true;
      description
        "The name of Network Security Function (NSF)";
    }
    uses nsf-capabilities;
  }
}
