// This file was generated by cs2yang.xsl
/*  This module has been generated by smidump 0.4.8. Do not edit.  */
module INET-ADDRESS-MIB {
  namespace "http://tail-f.com/ns/mibs/INET-ADDRESS-MIB/200502040000Z";
  prefix INET-ADDRESS-MIB;
  tailf:id "";
  tailf:snmp-mib-module-name INET-ADDRESS-MIB;


  import tailf-common {
    prefix tailf;
  }

  /* REVISION "200502040000Z" */
  revision 2005-02-04 {
    description "";
  }

  typedef InetAddressType {
    type enumeration {
      enum unknown {
        value 0;
      }
      enum ipv4 {
        value 1;
      }
      enum ipv6 {
        value 2;
      }
      enum ipv4z {
        value 3;
      }
      enum ipv6z {
        value 4;
      }
      enum dns {
        value 16;
      }
    }
  }
  typedef InetAddress {
    type tailf:hex-list {
      tailf:value-length "min .. 255";
    }
  }
  typedef InetAddressIPv4 {
    type string {
      pattern "((0|[1-9](([0-9]){0,2}))\.(0|[1-9](([0-9]){0,2}))\." +
        "(0|[1-9](([0-9]){0,2}))\.((0|[1-9](([0-9]){0,2}))))";
      length 4;
    }
  }
  typedef InetAddressIPv6 {
    type string {
      pattern "(((([0-9A-Fa-f]{2}){2}):(([0-9A-Fa-f]{2}){2}):" +
              "(([0-9A-Fa-f]{2}){2}):(([0-9A-Fa-f]{2}){2}):" +
              "(([0-9A-Fa-f]{2}){2}):(([0-9A-Fa-f]{2}){2}):" +
              "(([0-9A-Fa-f]{2}){2}):(([0-9A-Fa-f]{2})){15,15})" +
              "([0-9A-Fa-f]{2}))";
      length 16;
    }
  }
  typedef InetAddressIPv4z {
    type string {
      pattern "((0|[1-9](([0-9]){0,2}))\.(0|[1-9](([0-9]){0,2}))\." +
        "(0|[1-9](([0-9]){0,2}))\.(0|[1-9](([0-9]){0,2}))%" +
        "((0|[1-9](([0-9]){0,9})){3,3})(0|[1-9](([0-9]){0,9})))";
      length 8;
    }
  }
  typedef InetAddressIPv6z {
    type string {
      pattern "((([0-9A-Fa-f]{2}){2}):(([0-9A-Fa-f]{2}){2}):" +
        "(([0-9A-Fa-f]{2}){2}):(([0-9A-Fa-f]{2}){2}):" +
        "(([0-9A-Fa-f]{2}){2}):(([0-9A-Fa-f]{2}){2}):" +
        "(([0-9A-Fa-f]{2}){2}):(([0-9A-Fa-f]{2}){2})%" +
        "((0|[1-9](([0-9]){0,9})){3,3})(0|[1-9](([0-9]){0,9})))";
      length 20;
    }
  }
  typedef InetAddressDNS {
    type string {
      length "1 .. 255";
    }
  }
  typedef InetAddressPrefixLength {
    type uint32 {
      range "0 .. 2040";
    }
  }
  typedef InetPortNumber {
    type uint32 {
      range "0 .. 65535";
    }
  }
  typedef InetAutonomousSystemNumber {
    type uint32 {
      range "0 .. 4294967295";
    }
  }
  typedef InetScopeType {
    type enumeration {
      enum interfaceLocal {
        value 1;
      }
      enum linkLocal {
        value 2;
      }
      enum subnetLocal {
        value 3;
      }
      enum adminLocal {
        value 4;
      }
      enum siteLocal {
        value 5;
      }
      enum organizationLocal {
        value 8;
      }
      enum global {
        value 14;
      }
    }
  }
  typedef InetZoneIndex {
    type uint32 {
      range "0 .. 4294967295";
    }
  }
  typedef InetVersion {
    type enumeration {
      enum unknown {
        value 0;
      }
      enum ipv4 {
        value 1;
      }
      enum ipv6 {
        value 2;
      }
    }
  }
}
