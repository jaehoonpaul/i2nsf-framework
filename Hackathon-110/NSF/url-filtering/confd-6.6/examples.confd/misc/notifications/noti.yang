module noti {
  namespace "http://tail-f.com/ns/example/noti";
  prefix noti;

  import ietf-inet-types {
    prefix inet;
  }

  typedef Direction {
    type enumeration {
      enum dirty;
      enum clean;
    }
  }
  container root {
    leaf foo {
      type string;
      default fooo;
    }
    leaf bar {
      type int32;
      default 66;
    }
    container hosts {
      list host {
        key "hname hnum";
        max-elements 64;
        leaf hname {
          type string;
        }
        leaf hnum {
          type int32;
        }
        container servers {
          list server {
            key name;
            max-elements 64;
            leaf name {
              type string;
            }
            leaf ip {
              type inet:ipv4-address;
              mandatory true;
            }
            leaf port {
              type inet:port-number;
              mandatory true;
            }
            leaf dir {
              type Direction;
              mandatory true;
            }
          }
        }
      }
    }
  }
}
